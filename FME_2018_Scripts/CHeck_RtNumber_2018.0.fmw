FME workspace CHeck_RtNumber_2018.0.fmw

Parameters:
- SourceDataset_GEODATABASE_MDB = E:\Work\NRN\NRN\NRN.gdb   # Source Personal Geodatabase
- DestDataset_GEODATABASE_MDB =   # Destination Personal Geodatabase
- LOG_FILE =   # Log File

Readers:
- FILEGDB_1: FILEGDB from $(SourceDataset_GEODATABASE_MDB)

Writers:
- FILEGDB_2: FILEGDB to $(DestDataset_GEODATABASE_MDB)

FERRYSEG (reader FILEGDB_1)
    attributes: geodb_oid int, NID text(32), FERRYSEGID int, DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), OBJECTID int, SHAPE_Length double
    -> ATTRIBUTERENAMER_10
    -> ATTRIBUTERENAMER_9
    -> ATTRIBUTERENAMER_8
    -> ATTRIBUTERENAMER_7
    -> ATTRIBUTERENAMER_6
Note: Version de compilation : 5206 / --REVISION-- $Id: check_RtNumber_v2.fmw 1002 2010-04-08 19:01:46Z ddrolet $
Note: Nom du workbench : check_RtNumber_v2 / Auteur : Denis Bergeron / Guy Bergeron / Date de création : 24-déce-2004 / Description : Vérification de la continuité des réseaux numérotés.
Note: Transfert de l'attribut RTNUMBER5 / dans l'attribut RTNUMBER.
ATTRIBUTERENAMER_10: AttributeRenamer
    ATTR_TABLE = RENAME_SET_DEFAULT RTNUMBER5 > RTNUMBER
    -> AttributeTrimmer
Note: Transfert de l'attribut RTNUMBER4 / dans l'attribut RTNUMBER.
ATTRIBUTERENAMER_9: AttributeRenamer
    ATTR_TABLE = RENAME_SET_DEFAULT RTNUMBER4 > RTNUMBER
    -> AttributeTrimmer
Note: Transfert de l'attribut RTNUMBER3 / dans l'attribut RTNUMBER.
ATTRIBUTERENAMER_8: AttributeRenamer
    ATTR_TABLE = RENAME_SET_DEFAULT RTNUMBER3 > RTNUMBER
    -> AttributeTrimmer
Note: Transfert de l'attribut RTNUMBER2 / dans l'attribut RTNUMBER.
ATTRIBUTERENAMER_7: AttributeRenamer
    ATTR_TABLE = RENAME_SET_DEFAULT RTNUMBER2 > RTNUMBER
    -> AttributeTrimmer
Note: Transfert de l'attribut RTNUMBER1 / dans l'attribut RTNUMBER.
ATTRIBUTERENAMER_6: AttributeRenamer
    ATTR_TABLE = RENAME_SET_DEFAULT RTNUMBER1 > RTNUMBER
    -> AttributeTrimmer
ROADSEG (reader FILEGDB_1)
    attributes: geodb_oid int, NID text(32), ROADSEGID int, ADRANGENID text(32), DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES int, PAVSTATUS int, PAVSURF int,
      UNPAVSURF int, STRUCTID text(32), STRUCTTYPE int, STRUNAMEEN text(100), STRUNAMEFR text(100), OBJECTID int, SHAPE_Length double
    -> ATTRIBUTERENAMER_4
    -> ATTRIBUTERENAMER_3
    -> ATTRIBUTERENAMER_2
    -> ATTRIBUTERENAMER
    -> ATTRIBUTERENAMER_5
Note: Transfert de l'attribut RTNUMBER5 / dans l'attribut RTNUMBER.
ATTRIBUTERENAMER_5: AttributeRenamer
    ATTR_TABLE = RENAME_SET_DEFAULT RTNUMBER5 > RTNUMBER
    -> AttributeTrimmer
Note: Transfert de l'attribut RTNUMBER4 / dans l'attribut RTNUMBER.
ATTRIBUTERENAMER_4: AttributeRenamer
    ATTR_TABLE = RENAME_SET_DEFAULT RTNUMBER4 > RTNUMBER
    -> AttributeTrimmer
Note: Transfert de l'attribut RTNUMBER3 / dans l'attribut RTNUMBER.
ATTRIBUTERENAMER_3: AttributeRenamer
    ATTR_TABLE = RENAME_SET_DEFAULT RTNUMBER3 > RTNUMBER
    -> AttributeTrimmer
Note: Transfert de l'attribut RTNUMBER2 / dans l'attribut RTNUMBER.
ATTRIBUTERENAMER_2: AttributeRenamer
    ATTR_TABLE = RENAME_SET_DEFAULT RTNUMBER2 > RTNUMBER
    -> AttributeTrimmer
Note: Transfert de l'attribut RTNUMBER1 / dans l'attribut RTNUMBER.
ATTRIBUTERENAMER: AttributeRenamer
    ATTR_TABLE = RENAME_SET_DEFAULT RTNUMBER1 > RTNUMBER
    -> AttributeTrimmer
AttributeTrimmer
    SRC_ATTRS = RTNUMBER
    TRIM_CHARS = " "
    TRIM_TO_NONE = Yes
    TRIM_TYPE = Both
    -> TESTER
Note: Identification des segments / de routes à vérifier.
TESTER: Tester
    BOOL_OP = AND
    TEST_CLAUSE:
      TEST @Value(RTNUMBER) != -
      TEST @Value(RTNUMBER) != ?
      TEST @Value(RTNUMBER) != None
      TEST @Value(RTNUMBER) != Unknown
      TEST @Value(RTNUMBER) != ""
    PASSED -> LineJoiner
Note: Assemblage des lignes / selon les numéros de routes.
LineJoiner: LineCombiner
    ACCUM_ATTRS_NAME = Drop Incoming Attributes
    BREAK = no
    BREAK_CONNECTION_ACROSS_SETS = Yes
    CONNECT_Z_MODE = First Wins
    CONSIDER_NODE_ELEVATION = no
    DEAGGREGATE_GEOMETRY = Deaggregate
    GROUP_BY = RTNUMBER
    LINES_AS_SEGMENTS = No
    PRESERVE = no
    TOPOLOGY = End noded
    LINE -> COORDINATEROUNDER
Note: Arrondissement des coordonnées / à 7 nombres de décimales.
COORDINATEROUNDER: CoordinateRounder
    XPREC = 7
    YPREC = 7
    ZPREC = 0
    ROUNDED -> BUFFERER
Note: Création d'une surface groupée / sur l'attribut de réseau à valider.
BUFFERER: Bufferer
    ANGLE = 22.5
    CAP_STYLE = Round
    CORNER_STYLE = Round
    GROUP_BY = RTNUMBER
    MODE = AREA
    OFFSET = 0.0000001
    BUFFERED -> DEAGGREGATOR
Note: Désaggrégation de la surface. / Les surfaces qui ne se touchent pas / deviennent des surfaces distinctes.
DEAGGREGATOR: Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AGGREGATOR
Note: Réaggrégation des surfaces / groupées sur l'attribut de / réseau à valider.
AGGREGATOR: Aggregator
    ACCUM_ATTRS_NAME = Use Attributes From One Feature
    AGGREGATE_TYPE = Homogeneous Collection (If Possible)
    COUNT_ATTR = count_attribute
    GROUP_BY = RTNUMBER
    MODE = Geometry - Assemble One Level
    ORDERED = No
    SEP = ,
    AGGREGATE -> TESTER_7
Note: Sélection des / réseaux discontinus.
TESTER_7: Tester
    BOOL_OP = OR
    TEST_CLAUSE = TEST @Value(count_attribute) > 1
    PASSED -> DEAGGREGATOR_2
Note: Désaggrégation des réseaux / en erreurspour pouvoir / les visiter individuellement.
DEAGGREGATOR_2: Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> ATTRIBUTECREATOR_13
Note: Assignation d'un / commentaire d'erreur.
ATTRIBUTECREATOR_13: AttributeCreator
    ATTR_TABLE = SET_TO COMMENT = NETWORK: Check network continuity for Route Number &RTNUMBER
    -> RtNumber_Polygon_2 (writer FILEGDB_2)
RtNumber_Polygon_2 (writer FILEGDB_2)
    attributes: COMMENT text(64), SEVERITE int, ETAT int
