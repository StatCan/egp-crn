FME workspace Check_Reseaux_Isoles_2018.0.fmw

Parameters:
- SourceDataset_GEODATABASE_MDB = E:\Work\NRN\NRN\NRN.gdb   # Source Geodatabase (MDB) File(s)
- DestDataset_SHAPE =   # Destination ESRI Shape Directory
- LOG_FILE =   # Log File

Readers:
- FILEGDB_1: FILEGDB from $(SourceDataset_GEODATABASE_MDB)

Writers:
- ESRISHAPE_1: ESRISHAPE to $(DestDataset_SHAPE)

Note: Version de compilation : 56202 / --REVISION-- $Id: Check_reseaux_isoles.fmw 1649 2012-03-16 14:46:43Z ddrolet $
Note: Nom du workbench : check_reseaux_isoles / Auteur : Diane Drolet / Date de création : 10 février 2011 / Description : Workbench qui identifie les différents réseaux d un jeu de données, il tient compte des segments routiers et des segments de liaison par transbordeur.
ROADSEG (reader FILEGDB_1)
    attributes: geodb_oid int, OBJECTID int, NID text(32), ROADSEGID int, ADRANGENID text(32), DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES int, PAVSTATUS int,
      PAVSURF int, UNPAVSURF int, STRUCTID text(32), STRUCTTYPE int, STRUNAMEEN text(100), STRUNAMEFR text(100), SHAPE_Length double
    -> CoordinateRounder
FERRYSEG (reader FILEGDB_1)
    attributes: geodb_oid int, OBJECTID int, NID text(32), FERRYSEGID int, DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), SHAPE_Length double
    -> CoordinateRounder
CoordinateRounder
    XPREC = 7
    YPREC = 7
    ZPREC = 0
    ROUNDED -> NetworkTopologyBuilder [LINE]
NetworkTopologyBuilder: NetworkTopologyCalculator
    NETWORK_ID_ATTR = NETWORK_ID
    NETWORK -> Aggregator
Aggregator
    ACCUM_ATTRS_NAME = Use Attributes From One Feature
    AGGREGATE_TYPE = Homogeneous Collection (If Possible)
    COUNT_ATTR = count_attribute
    GROUP_BY = NETWORK_ID
    MODE = Geometry - Assemble One Level
    ORDERED = No
    SEP = ,
    AGGREGATE -> TESTER_7
Note: Sélection des / réseaux isolés.
TESTER_7: Tester
    BOOL_OP = OR
    TEST_CLAUSE = TEST @Value(count_attribute) > 1
    PASSED -> Concatenator
Note: Assignation d'un / commentaire d'erreur.
Concatenator: StringConcatenator
    ACTION = Create New Attribute
    PARM_LINE = NETWORK: Check isolated network: @Value(count_attribute)
    VAL_ATTR = COMMENT
    -> Reseaux_isoles_1 (writer ESRISHAPE_1)
Reseaux_isoles_1 (writer ESRISHAPE_1)
    attributes: NID char(32), COMMENT char(132), SEVERITE number(4,0), ETAT number(4,0)
