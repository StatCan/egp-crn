FME workspace Check_Provi_1_2018.0.fmw

Parameters:
- SourceDataset_GEODATABASE_MDB = E:\Work\NRN\NRN\NRN.gdb   # Source Personal Geodatabase
- DestDataset_SHAPE =   # Destination Shape File Directory
- LOG_FILE =   # Log File

Readers:
- FILEGDB_1: FILEGDB from $(SourceDataset_GEODATABASE_MDB)

Writers:
- NULL_1: NULL
- ESRISHAPE_1: ESRISHAPE to $(DestDataset_SHAPE)

Note: Version de compilation : 5206 / --REVISION-- $Id: check_proxi_1_v2.fmw 3562 2017-03-28 12:05:04Z jhuot $
Note: Nom du workbench : check_proxi_1_v2 / Auteur : Denis Bergeron / Guy Bergeron / Diane Drolet / Date de création : 02-nove-2004 / Description : Vérification des duplications et des proximités de points et de lignes.
FERRYSEG (reader FILEGDB_1)
    attributes: geodb_oid int, NID text(32), FERRYSEGID int, DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), OBJECTID int, SHAPE_Length double
    -> LINEJOINER_2
ROADSEG (reader FILEGDB_1)
    attributes: geodb_oid int, NID text(32), ROADSEGID int, ADRANGENID text(32), DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES int, PAVSTATUS int, PAVSURF int,
      UNPAVSURF int, STRUCTID text(32), STRUCTTYPE int, STRUNAMEEN text(100), STRUNAMEFR text(100), OBJECTID int, SHAPE_Length double
    -> LINEJOINER_2
Note: Assemblage des lignes.
LINEJOINER_2: LineCombiner
    ACCUM_ATTRS_NAME = Drop Incoming Attributes
    BREAK = no
    BREAK_CONNECTION_ACROSS_SETS = Yes
    CONNECT_Z_MODE = First Wins
    CONSIDER_NODE_ELEVATION = no
    DEAGGREGATE_GEOMETRY = Deaggregate
    LINES_AS_SEGMENTS = No
    PRESERVE = no
    TOPOLOGY = End noded
    LINE -> REPROJECTOR_3
Note: Transfert des coordonnées / dans la projection LCC.
REPROJECTOR_3: Reprojector
    DEST = CANLAMB-CSRS
    INTERPOLATION_TYPE_NAME = Nearest Neighbor
    RASTER_CELL_SIZE = Preserve Cells
    RASTER_TOLERANCE = 0.0
    SOURCE = LLCSRS
    REPROJECTED -> Quadtree
    REPROJECTED -> Clipper [CLIPPEE]
Note: Génération de tuiles selon / le principe du Quadtree.
Quadtree
    MAX_ELEMENT = 100000
    NOM_TUILE = nom_tuile
    TUILES -> Clipper [CLIPPER]
    TUILES -> Quadtree_2
Quadtree_2: Inspector [off]
Note: Découpage des lignes / selon les tuiles.
Clipper
    ATTR_ACCUM_MODE = Prefix Clipper
    BOUNDARY_CASES = Treat as Inside
    CLEANING_TOLERANCE = None
    CLIPPED_ATTR = _clipped
    CLIPPER_PREFIX = clipper_
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> Cloner
Cloner
    COPIES = 1
    COPYATT = _copynum
    COPY -> BUFFERER
    COPY -> LINEONAREAOVERLAYER [LINE]
    COPY -> Cloner_2
Cloner_2: Inspector [off]
Note: Création d'un buffer de 3m / autour des lignes.
BUFFERER: Bufferer
    ANGLE = 22.5
    CAP_STYLE = Round
    CORNER_STYLE = Round
    MODE = AREA
    OFFSET = 3
    BUFFERED -> LINEONAREAOVERLAYER [AREA]
Note: Ajout d'un attribut pour vérifier / la proximité des lignes.
LINEONAREAOVERLAYER: LineOnAreaOverlayer
    ATTR_ACCUM_MODE = Merge Incoming
    ATTR_CONFLICT_RES = Use Original
    CLEANING_TOLERANCE = None
    DEAGGREGATE_INPUT = Yes
    GROUP_BY = clipper_NOM_TUILE
    OV_ATTR = OVERLAPSA
    LINE -> OVERLAPS (writer ESRISHAPE_1)
    AREA -> Null_Area (writer NULL_1)
OVERLAPS (writer ESRISHAPE_1)
    attributes: OVERLAPSA number(20,0)
Null_Area (writer NULL_1)
