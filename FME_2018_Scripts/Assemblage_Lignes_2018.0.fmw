FME workspace Assemblage_Lignes_2018.0.fmw

Parameters:
- SourceDataset_GEODATABASE_MDB = E:\Work\NRN\NRN\NRN.gdb   # Source Personal Geodatabase
- DestDataset_GEODATABASE_MDB =   # Destination Personal Geodatabase
- LOG_FILE =   # Log File

Readers:
- FILEGDB_1: FILEGDB from $(SourceDataset_GEODATABASE_MDB)

Writers:
- FILEGDB_2: FILEGDB to $(DestDataset_GEODATABASE_MDB)

Note: Version de compilation : 5206 / --REVISION-- $Id: assemblage_lignes.fmw 1646 2012-03-14 18:01:09Z ddrolet $
Note: Nom du workbench : assemblage_lignes.fmw / Auteur : Denis Bergeron / Date de création : 20-mai-2008 / Description : Assemblage des lignes qui ont tous les mêmes attributs et arrondissement des coordonnées à 7 nombre de décimales.
FERRYSEG (reader FILEGDB_1)
    attributes: geodb_oid int, OBJECTID int, NID text(32), FERRYSEGID int, DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), Shape_Length double, CLOSING int
    -> COORDINATEROUNDER_4
Note: Arrondissement des / coordonnées à 7 décimales.
COORDINATEROUNDER_4: CoordinateRounder
    XPREC = 7
    YPREC = 7
    ZPREC = 0
    ROUNDED -> LINEJOINER
Note: Assemblage des lignes
LINEJOINER: LineCombiner
    ACCUM_ATTRS_NAME = Drop Incoming Attributes
    BREAK = no
    BREAK_CONNECTION_ACROSS_SETS = No
    CONNECT_Z_MODE = First Wins
    CONSIDER_NODE_ELEVATION = no
    DEAGGREGATE_GEOMETRY = Deaggregate
    GROUP_BY = RTENAME1FR fme_feature_type CREDATE CLOSING RTENAME4FR DATASETNAM ROADCLASS RTNUMBER5 RTNUMBER1 RTENAME2EN RTENAME4EN RTNUMBER2 RTNUMBER4 REVDATE RTENAME3FR NID ACQTECH RTNUMBER3 RTENAME3EN SPECVERS ACCURACY PROVIDER RTENAME1EN RTENAME2FR METACOVER
    LINES_AS_SEGMENTS = No
    PRESERVE = yes
    TOPOLOGY = End noded
    LINE -> COUNTER
Note: Ajout de l'attribut / FERRYSEGID.
COUNTER: Counter
    CNT_ATTR = FERRYSEGID
    DOMAIN = counter
    SCOPE = Global
    START = 1
    -> FERRYSEG (writer FILEGDB_2)
FERRYSEG (writer FILEGDB_2)
    attributes: NID text(32), FERRYSEGID int, DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), Shape_Length double, CLOSING int
ROADSEG (reader FILEGDB_1)
    attributes: geodb_oid int, OBJECTID int, NID text(32), ROADSEGID int, ADRANGENID text(32), DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES int, PAVSTATUS int,
      PAVSURF int, UNPAVSURF int, STRUCTID text(32), STRUCTTYPE int, STRUNAMEEN text(100), STRUNAMEFR text(100), Shape_Length double, CLOSING int, ROADJURIS text(100), SPEED int, TRAFFICDIR int
    -> COORDINATEROUNDER_5
Note: Arrondissement des / coordonnées à 7 décimales.
COORDINATEROUNDER_5: CoordinateRounder
    XPREC = 7
    YPREC = 7
    ZPREC = 0
    ROUNDED -> AreaBuilder
    ROUNDED -> LINEONAREAOVERLAYER [LINE]
Note: Création de polygones.
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    GROUP_BY = NID
    LINES_AS_SEGMENTS = No
    POLY_ACCUM_ATTRS_NAME = Drop Incoming Attributes
    SNAPTYPE_PARAM = None
    AREA -> LINEONAREAOVERLAYER [AREA]
Note: Superposition des lignes et des polygones / afin de déterminer celles qui partagent.
LINEONAREAOVERLAYER: LineOnAreaOverlayer
    ATTR_ACCUM_MODE = Merge Incoming
    ATTR_CONFLICT_RES = Use Original
    CLEANING_TOLERANCE = None
    DEAGGREGATE_INPUT = Yes
    OV_ATTR = _overlaps_area
    LINE -> TESTER
Note: Sélection des lignes.
TESTER: Tester
    BOOL_OP = OR
    TEST_CLAUSE = TEST @Value(_overlaps_area) = 0
    PASSED -> LINEJOINER_2
    FAILED -> COUNTER_2
Note: Assemblage des lignes.
LINEJOINER_2: LineCombiner
    ACCUM_ATTRS_NAME = Drop Incoming Attributes
    BREAK = no
    BREAK_CONNECTION_ACROSS_SETS = No
    CONNECT_Z_MODE = First Wins
    CONSIDER_NODE_ELEVATION = no
    DEAGGREGATE_GEOMETRY = Deaggregate
    GROUP_BY = RTENAME1FR CLOSING CREDATE RTENAME4FR DATASETNAM ROADCLASS RTNUMBER5 STRUNAMEEN RTNUMBER1 RTENAME2EN RTENAME4EN RTNUMBER2 RTNUMBER4 REVDATE ROADJURIS RTENAME3FR PAVSTATUS PAVSURF NID ACQTECH SPEED STRUNAMEFR RTNUMBER3 RTENAME3EN NBRLANES ADRANGENID SPECVERS ACCURACY STRUCTID TRAFFICDIR UNPAVSURF PROVIDER RTENAME1EN RTENAME2FR METACOVER EXITNBR STRUCTTYPE
    LINES_AS_SEGMENTS = No
    PRESERVE = yes
    TOPOLOGY = End noded
    LINE -> COUNTER_2
Note: Ajout de l'attribut / ROADSEGID.
COUNTER_2: Counter
    CNT_ATTR = ROADSEGID
    DOMAIN = counter
    SCOPE = Global
    START = 1
    -> ROADSEG (writer FILEGDB_2)
ROADSEG (writer FILEGDB_2)
    attributes: NID text(32), ROADSEGID int, ADRANGENID text(32), DATASETNAM int, SPECVERS text(100), ACQTECH int, ACCURACY int, PROVIDER int, CREDATE text(8), REVDATE text(8), METACOVER int, ROADCLASS int, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES int, PAVSTATUS int, PAVSURF int, UNPAVSURF int,
      STRUCTID text(32), STRUCTTYPE int, STRUNAMEEN text(100), STRUNAMEFR text(100), Shape_Length double, CLOSING int, ROADJURIS text(100), SPEED int, TRAFFICDIR int
TOLLPOINT (reader FILEGDB_1)
    attributes: geodb_oid int, OBJECTID int, NID text(32), DATASETNAM int, SPECVERS text(100), ACQTECH int, ACCURACY int, PROVIDER int, CREDATE text(8), REVDATE text(8), METACOVER int, TOLLPTTYPE int, ROADNID text(32)
    -> COORDINATEROUNDER_2
Note: Arrondissement des / coordonnées à 7 décimales.
COORDINATEROUNDER_2: CoordinateRounder
    XPREC = 7
    YPREC = 7
    ZPREC = 0
    ROUNDED -> TOLLPOINT (writer FILEGDB_2)
TOLLPOINT (writer FILEGDB_2)
    attributes: NID text(32), DATASETNAM int, SPECVERS text(100), ACQTECH int, ACCURACY int, PROVIDER int, CREDATE text(8), REVDATE text(8), METACOVER int, TOLLPTTYPE int, ROADNID text(32)
JUNCTION (reader FILEGDB_1)
    attributes: geodb_oid int, OBJECTID int, NID text(32), DATASETNAM int, SPECVERS text(100), ACQTECH int, ACCURACY int, PROVIDER int, CREDATE text(8), REVDATE text(8), METACOVER int, JUNCTYPE int, EXITNBR text(10)
    -> COORDINATEROUNDER_3
Note: Arrondissement des / coordonnées à 7 décimales.
COORDINATEROUNDER_3: CoordinateRounder
    XPREC = 7
    YPREC = 7
    ZPREC = 0
    ROUNDED -> JUNCTION (writer FILEGDB_2)
JUNCTION (writer FILEGDB_2)
    attributes: NID text(32), DATASETNAM int, SPECVERS text(100), ACQTECH int, ACCURACY int, PROVIDER int, CREDATE text(8), REVDATE text(8), METACOVER int, JUNCTYPE int, EXITNBR text(10)
BLKPASSAGE (reader FILEGDB_1)
    attributes: geodb_oid int, OBJECTID int, NID text(32), DATASETNAM int, SPECVERS text(100), ACQTECH int, ACCURACY int, PROVIDER int, CREDATE text(8), REVDATE text(8), METACOVER int, BLKPASSTY int, ROADNID text(32)
    -> COORDINATEROUNDER
Note: Arrondissement des / coordonnées à 7 décimales.
COORDINATEROUNDER: CoordinateRounder
    XPREC = 7
    YPREC = 7
    ZPREC = 0
    ROUNDED -> BLKPASSAGE (writer FILEGDB_2)
BLKPASSAGE (writer FILEGDB_2)
    attributes: NID text(32), DATASETNAM int, SPECVERS text(100), ACQTECH int, ACCURACY int, PROVIDER int, CREDATE text(8), REVDATE text(8), METACOVER int, BLKPASSTY int, ROADNID text(32)
CROSSING (reader FILEGDB_1)
    attributes: geodb_oid int, OBJECTID int, NID text(32), DATASETNAM int, SPECVERS text(100), ACQTECH int, ACCURACY int, PROVIDER int, CREDATE text(8), REVDATE text(8), METACOVER int, ROADNID text(32), TYPE int
    -> COORDINATEROUNDER_6
Note: Arrondissement des / coordonnées à 7 décimales.
COORDINATEROUNDER_6: CoordinateRounder
    XPREC = 7
    YPREC = 7
    ZPREC = 0
    ROUNDED -> CROSSING (writer FILEGDB_2)
CROSSING (writer FILEGDB_2)
    attributes: geodb_oid int, OBJECTID int, NID text(32), DATASETNAM int, SPECVERS text(100), ACQTECH int, ACCURACY int, PROVIDER int, CREDATE text(8), REVDATE text(8), METACOVER int, ROADNID text(32), TYPE int
STRPLANAME (reader FILEGDB_1)
    attributes: geodb_oid int, OBJECTID int, NID text(32), DATASETNAM int, SPECVERS text(100), ACQTECH int, ACCURACY int, PROVIDER int, CREDATE text(8), REVDATE text(8), METACOVER int, DIRPREFIX int, STRTYPRE text(30), STARTICLE text(20), NAMEBODY text(50), STRTYSUF text(30), DIRSUFFIX int, MUNIQUAD int, PLACENAME text(100), PROVINCE int, PLACETYPE text(100)
    -> STRPLANAME (writer FILEGDB_2)
STRPLANAME (writer FILEGDB_2)
    attributes: NID text(32), DATASETNAM int, SPECVERS text(100), ACQTECH int, ACCURACY int, PROVIDER int, CREDATE text(8), REVDATE text(8), METACOVER int, DIRPREFIX int, STRTYPRE text(30), STARTICLE text(20), NAMEBODY text(50), STRTYSUF text(30), DIRSUFFIX int, MUNIQUAD int, PLACENAME text(100), PROVINCE int, PLACETYPE text(100)
ALTNAMLINK (reader FILEGDB_1)
    attributes: geodb_oid int, OBJECTID int, NID text(32), STRNAMENID text(32), DATASETNAM int, SPECVERS text(100), CREDATE text(8), REVDATE text(8)
    -> ALTNAMLINK (writer FILEGDB_2)
ALTNAMLINK (writer FILEGDB_2)
    attributes: NID text(32), STRNAMENID text(32), DATASETNAM int, SPECVERS text(100), CREDATE text(8), REVDATE text(8)
ADDRANGE (reader FILEGDB_1)
    attributes: geodb_oid int, OBJECTID int, NID text(32), DATASETNAM int, SPECVERS text(100), ACQTECH int, ACCURACY int, PROVIDER int, CREDATE text(8), REVDATE text(8), METACOVER int, L_DIGDIRFG int, L_HNUMSTR int, L_RFSYSIND int, L_HNUMTYPF int, L_HNUMF int, L_HNUMSUFF text(20), L_HNUMTYPL int, L_HNUML int, L_HNUMSUFL text(20), L_OFFNANID text(32), L_ALTNANID text(32), R_DIGDIRFG int, R_HNUMSTR int, R_RFSYSIND int, R_HNUMTYPF int, R_HNUMF int, R_HNUMSUFF text(20), R_HNUMTYPL int, R_HNUML int,
      R_HNUMSUFL text(20), R_OFFNANID text(32), R_ALTNANID text(32)
    -> ADDRANGE (writer FILEGDB_2)
ADDRANGE (writer FILEGDB_2)
    attributes: NID text(32), DATASETNAM int, SPECVERS text(100), ACQTECH int, ACCURACY int, PROVIDER int, CREDATE text(8), REVDATE text(8), METACOVER int, L_DIGDIRFG int, L_HNUMSTR int, L_RFSYSIND int, L_HNUMTYPF int, L_HNUMF int, L_HNUMSUFF text(20), L_HNUMTYPL int, L_HNUML int, L_HNUMSUFL text(20), L_OFFNANID text(32), L_ALTNANID text(32), R_DIGDIRFG int, R_HNUMSTR int, R_RFSYSIND int, R_HNUMTYPF int, R_HNUMF int, R_HNUMSUFF text(20), R_HNUMTYPL int, R_HNUML int, R_HNUMSUFL text(20), R_OFFNANID text(32),
      R_ALTNANID text(32)
