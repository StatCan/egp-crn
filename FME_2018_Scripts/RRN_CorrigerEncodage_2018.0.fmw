FME workspace RRN_CorrigerEncodage_2018.0.fmw

Parameters:
- IN_ROADSEG_SHP = E:\Work\NRN\NRN_PE_201703_deliverable\ROADSEG.shp
- IN_FERRYSEG_SHP = E:\Work\NRN\NRN_PE_201703_deliverable\FERRYSEG.shp
- IN_STRPLANAME_DBF =
- OUT_ROADSEG_SHP =
- OUT_FERRYSEG_SHP =
- OUT_STRPLANAME_DBF =
- LOG_FILE =

Readers:
- ESRISHAPE_1: ESRISHAPE from $(IN_ROADSEG_SHP)
- ESRISHAPE_2: ESRISHAPE from $(IN_FERRYSEG_SHP)
- DBF_1: DBF from $(IN_STRPLANAME_DBF)

Writers:
- ESRISHAPE_3: ESRISHAPE to $(OUT_ROADSEG_SHP)
- ESRISHAPE_4: ESRISHAPE to $(OUT_FERRYSEG_SHP)
- DBF_3: DBF to $(OUT_STRPLANAME_DBF)

Note: Version de compilation : 6501 / -- REVISION -- $Id: RRN_RRN_CorrigerEncodage.fmw 172 2009-02-09 19:25:35Z gutrembl$
Note: Nom du workbench : RRN_CorrigerEncodage.fmw / Auteur : gutrembl / Date de création : 13 janvier 2012 / Description : / Certains fichiers en provenance de provinces peuvent contenir des caractères / qui sont illégaux dans plusieurs attributs tels que RTENAME1FR, STRUNAMEFR, / ROADJURIS, etc. Cette situation est causée par un mauvais encodage et est / systématique. Il faut donc remplacer ces caractères par des caractères légaux. / Ce remplacement se fait utilisant le transformer StringPairReplacer qui fait / un jumelage entre les caractères illégaaux et ceux qui sont légaux (Peuvent / être un duo de caractères ou un caractère simple).
AttributeCreator
    ATTR_TABLE = SET_TO origine = ROADSEG
    -> AttributeCopier
AttributeCreator_3
    ATTR_TABLE = SET_TO origine = FERRYSEG
    -> AttributeCopier
Note: Ce programme utilise un Custom Transformer dans le but de faciliter la mise à jour / (Ajout de nouveaux caractères problématiques). Lorsque de nouveaux caractères / sont rencontrés (signalé par le Terminator) il peut être nécessaire de mettre à jour / le transformer StringPairReplacer dans le Custom transformer.
AttributeCopier_9
    ATTR_TABLE = COPY STRUNAMEFR > ENCODAGE
    -> ENCODAGE_RRN_5 [StringPairReplacer_INPUT_175]
ENCODAGE_RRN_5
    SRC_ATTR = ENCODAGE
    -> AttributeRenamer_11
AttributeRenamer_11
    ATTR_TABLE = RENAME_SET_DEFAULT ENCODAGE > STRUNAMEFR
    -> AttributeCopier_10
AttributeCopier_10
    ATTR_TABLE = COPY STRUNAMEEN > ENCODAGE
    -> ENCODAGE_RRN_17 [StringPairReplacer_INPUT_175]
ENCODAGE_RRN_17
    SRC_ATTR = ENCODAGE
    -> AttributeRenamer_17
AttributeRenamer_17
    ATTR_TABLE = RENAME_SET_DEFAULT ENCODAGE > STRUNAMEEN
    -> AttributeCopier_11
AttributeCopier_11
    ATTR_TABLE = COPY ROADJURIS > ENCODAGE
    -> ENCODAGE_RRN_6 [StringPairReplacer_INPUT_175]
ENCODAGE_RRN_6
    SRC_ATTR = ENCODAGE
    -> AttributeRenamer_12
AttributeRenamer_12
    ATTR_TABLE = RENAME_SET_DEFAULT ENCODAGE > ROADJURIS
    -> AttributeCopier_2
AttributeCreator_2
    ATTR_TABLE = SET_TO origine = STRPLANAME
    -> AttributeCopier_13
AttributeCopier_13
    ATTR_TABLE = COPY STRTYPRE > ENCODAGE
    -> ENCODAGE_RRN_7 [StringPairReplacer_INPUT_175]
ENCODAGE_RRN_7
    SRC_ATTR = ENCODAGE
    -> AttributeRenamer
AttributeRenamer
    ATTR_TABLE = RENAME_SET_DEFAULT ENCODAGE > STRTYPRE
    -> AttributeCopier_15
AttributeCopier_15
    ATTR_TABLE = COPY STARTICLE > ENCODAGE
    -> ENCODAGE_RRN_8 [StringPairReplacer_INPUT_175]
ENCODAGE_RRN_8
    SRC_ATTR = ENCODAGE
    -> AttributeRenamer_2
AttributeRenamer_2
    ATTR_TABLE = RENAME_SET_DEFAULT ENCODAGE > STARTICLE
    -> AttributeCopier_17
AttributeCopier_17
    ATTR_TABLE = COPY NAMEBODY > ENCODAGE
    -> ENCODAGE_RRN_9 [StringPairReplacer_INPUT_175]
ENCODAGE_RRN_9
    SRC_ATTR = ENCODAGE
    -> AttributeRenamer_3
AttributeRenamer_3
    ATTR_TABLE = RENAME_SET_DEFAULT ENCODAGE > NAMEBODY
    -> AttributeCopier_19
AttributeCopier_19
    ATTR_TABLE = COPY STRTYSUF > ENCODAGE
    -> ENCODAGE_RRN_10 [StringPairReplacer_INPUT_175]
ENCODAGE_RRN_10
    SRC_ATTR = ENCODAGE
    -> AttributeRenamer_4
AttributeRenamer_4
    ATTR_TABLE = RENAME_SET_DEFAULT ENCODAGE > STRTYSUF
    -> AttributeCopier_21
AttributeCopier_21
    ATTR_TABLE = COPY PLACENAME > ENCODAGE
    -> ENCODAGE_RRN_11 [StringPairReplacer_INPUT_175]
ENCODAGE_RRN_11
    SRC_ATTR = ENCODAGE
    -> AttributeRenamer_5
AttributeRenamer_5
    ATTR_TABLE = RENAME_SET_DEFAULT ENCODAGE > PLACENAME
    -> AttributeCopier_23
AttributeCopier_23
    ATTR_TABLE = COPY PLACETYPE > ENCODAGE
    -> ENCODAGE_RRN_12 [StringPairReplacer_INPUT_175]
ENCODAGE_RRN_12
    SRC_ATTR = ENCODAGE
    -> AttributeRenamer_6
AttributeRenamer_6
    ATTR_TABLE = RENAME_SET_DEFAULT ENCODAGE > PLACETYPE
    -> FeatureHolder
FeatureHolder
    -> AttributeFilter
    -> StringReplacer
AttributeFilter
    ATTR_NAME = origine
    ATTR_VALUES = ROADSEG,FERRYSEG,STRPLANAME
    ROADSEG -> ROADSEG (writer ESRISHAPE_3)
    FERRYSEG -> FERRYSEG (writer ESRISHAPE_4)
    STRPLANAME -> STRPLANAME (writer DBF_3)

Bookmark: ROADSEG
ROADSEG (reader ESRISHAPE_1)
    attributes: NID char(32), ROADSEGID number(9,0), ADRANGENID char(32), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0),
      STRUCTID char(32), STRUCTTYPE number(4,0), STRUNAMEEN char(100), STRUNAMEFR char(100), TRAFFICDIR number(4,0), ROADJURIS char(100), CLOSING number(4,0), SPEED number(4,0), ID number(11,0), NORTE char(5), CLASSERTE char(40), GAUMUNNOM char(64), DROMUNNOM char(64), GAUODOGENE char(20), GAUODOPART char(8), GAUODOSPEC char(30), GAUODOORIE char(15), GAUODORECO char(60), GAUPARITE char(1), GAUMINADRE number(11,0), GAUMINSUFF char(3), GAUMAXADRE number(11,0), GAUMAXSUFF char(3), DROODOGENE char(20), DROODOPART char(8), DROODOSPEC char(30), DROODOORIE char(15), DROODORECO char(60), DROPARITE char(1), DROMINADRE number(11,0),
      DROMINSUFF char(3), DROMAXADRE number(6,0), DROMAXSUFF char(3), ISN char(20), ISR char(20), CREATION char(20), REVISION char(20), FOURNISSEU char(20), PREC_PLANI char(20), TECH_ACQUI char(20), PARTICULAR char(64), NUM_SORTIE char(24), ID_NUM_SOR char(64)
    -> AttributeCreator

Bookmark: FERRYSEG
FERRYSEG (reader ESRISHAPE_2)
    attributes: NID char(32), FERRYSEGID number(9,0), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), CLOSING number(4,0)
    -> AttributeCreator_3

Bookmark: RTENAME_FR
AttributeCopier
    ATTR_TABLE = COPY RTENAME1FR > ENCODAGE
    -> ENCODAGE_RRN [StringPairReplacer_INPUT_175]
ENCODAGE_RRN
    SRC_ATTR = ENCODAGE
    -> AttributeRenamer_7
AttributeRenamer_7
    ATTR_TABLE = RENAME_SET_DEFAULT ENCODAGE > RTENAME1FR
    -> AttributeCopier_3
AttributeCopier_3
    ATTR_TABLE = COPY RTENAME2FR > ENCODAGE
    -> ENCODAGE_RRN_2 [StringPairReplacer_INPUT_175]
ENCODAGE_RRN_2
    SRC_ATTR = ENCODAGE
    -> AttributeRenamer_8
AttributeRenamer_8
    ATTR_TABLE = RENAME_SET_DEFAULT ENCODAGE > RTENAME2FR
    -> AttributeCopier_5
AttributeCopier_5
    ATTR_TABLE = COPY RTENAME3FR > ENCODAGE
    -> ENCODAGE_RRN_3 [StringPairReplacer_INPUT_175]
ENCODAGE_RRN_3
    SRC_ATTR = ENCODAGE
    -> AttributeRenamer_9
AttributeRenamer_9
    ATTR_TABLE = RENAME_SET_DEFAULT ENCODAGE > RTENAME3FR
    -> AttributeCopier_7
AttributeCopier_7
    ATTR_TABLE = COPY RTENAME4FR > ENCODAGE
    -> ENCODAGE_RRN_4 [StringPairReplacer_INPUT_175]
ENCODAGE_RRN_4
    SRC_ATTR = ENCODAGE
    -> AttributeRenamer_10
AttributeRenamer_10
    ATTR_TABLE = RENAME_SET_DEFAULT ENCODAGE > RTENAME4FR
    -> AttributeCopier_9

Bookmark: RTENAME_EN
AttributeCopier_2
    ATTR_TABLE = COPY RTENAME1EN > ENCODAGE
    -> ENCODAGE_RRN_13 [StringPairReplacer_INPUT_175]
ENCODAGE_RRN_13
    SRC_ATTR = ENCODAGE
    -> AttributeRenamer_13
AttributeRenamer_13
    ATTR_TABLE = RENAME_SET_DEFAULT ENCODAGE > RTENAME1EN
    -> AttributeCopier_4
AttributeCopier_4
    ATTR_TABLE = COPY RTENAME2EN > ENCODAGE
    -> ENCODAGE_RRN_14 [StringPairReplacer_INPUT_175]
ENCODAGE_RRN_14
    SRC_ATTR = ENCODAGE
    -> AttributeRenamer_14
AttributeRenamer_14
    ATTR_TABLE = RENAME_SET_DEFAULT ENCODAGE > RTENAME2EN
    -> AttributeCopier_6
AttributeCopier_6
    ATTR_TABLE = COPY RTENAME3EN > ENCODAGE
    -> ENCODAGE_RRN_15 [StringPairReplacer_INPUT_175]
ENCODAGE_RRN_15
    SRC_ATTR = ENCODAGE
    -> AttributeRenamer_15
AttributeRenamer_15
    ATTR_TABLE = RENAME_SET_DEFAULT ENCODAGE > RTENAME3EN
    -> AttributeCopier_8
AttributeCopier_8
    ATTR_TABLE = COPY RTENAME4EN > ENCODAGE
    -> ENCODAGE_RRN_16 [StringPairReplacer_INPUT_175]
ENCODAGE_RRN_16
    SRC_ATTR = ENCODAGE
    -> AttributeRenamer_16
AttributeRenamer_16
    ATTR_TABLE = RENAME_SET_DEFAULT ENCODAGE > RTENAME4EN
    -> FeatureHolder

Bookmark: STRPLANAME
STRPLANAME (reader DBF_1)
    attributes: NID char(32), DATASETNAM number(4,0), SPECVERS char(100), ACQTECH number(4,0), ACCURACY number(4,0), PROVIDER number(4,0), CREDATE char(8), REVDATE char(8), METACOVER number(4,0), DIRPREFIX number(4,0), STRTYPRE char(30), STARTICLE char(20), NAMEBODY char(50), STRTYSUF char(30), DIRSUFFIX number(4,0), MUNIQUAD number(4,0), PLACENAME char(100), PROVINCE number(4,0), PLACETYPE char(100)
    -> AttributeCreator_2

Bookmark: ROADSEG
ROADSEG (writer ESRISHAPE_3)
    attributes: NID char(32), ROADSEGID number(9,0), ADRANGENID char(32), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0),
      STRUCTID char(32), STRUCTTYPE number(4,0), STRUNAMEEN char(100), STRUNAMEFR char(100), TRAFFICDIR number(4,0), ROADJURIS char(100), CLOSING number(4,0), SPEED number(4,0)

Bookmark: FERRYSEG
FERRYSEG (writer ESRISHAPE_4)
    attributes: NID char(32), FERRYSEGID number(9,0), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), CLOSING number(4,0)

Bookmark: STRPLANAME
STRPLANAME (writer DBF_3)
    attributes: NID char(32), DATASETNAM number(4,0), SPECVERS char(100), ACQTECH number(4,0), ACCURACY number(4,0), PROVIDER number(4,0), CREDATE char(8), REVDATE char(8), METACOVER number(4,0), DIRPREFIX number(4,0), STRTYPRE char(30), STARTICLE char(20), NAMEBODY char(50), STRTYSUF char(30), DIRSUFFIX number(4,0), MUNIQUAD number(4,0), PLACENAME char(100), PROVINCE number(4,0), PLACETYPE char(100)

Bookmark: Enlève bons caractères pour tester
Note: On subtilise tous les caractères / légaux par un vide et ceux qui / restent sont des caractères / illégaux qui devront être / modifiés manuellement.
StringReplacer
    CASE = YES
    FIND_TEXT = [-a-zA-Z0123456789., ôöäóéèêëàâçùúûüïîÔÖÄÓÉÈÊËÀÂÇÙÚÛÜ Ï Î'+ /&!_'()?#: ]
    NO_MATCH = _FME_NO_OP_
    REGEXP = YES
    SRC_ATTRS = NAMEBODY,PLACENAME,PLACETYPE,ROADJURIS,RTENAME1FR,RTENAME2FR,RTENAME3FR,RTENAME4FR,STARTICLE,STRTYPRE,STRTYSUF,STRUNAMEFR
    -> Tester
Tester
    BOOL_OP = OR
    TEST_CLAUSE:
      STRING_TEST @Value(RTENAME1FR) != ""
      STRING_TEST @Value(RTENAME2FR) != ""
      STRING_TEST @Value(RTENAME3FR) != ""
      STRING_TEST @Value(RTENAME4FR) != ""
      STRING_TEST @Value(ROADJURIS) != ""
      STRING_TEST @Value(STRUNAMEFR) != ""
      STRING_TEST @Value(STRTYPRE) != ""
      STRING_TEST @Value(STARTICLE) != ""
      STRING_TEST @Value(NAMEBODY) != ""
      STRING_TEST @Value(STRTYSUF) != ""
      STRING_TEST @Value(PLACENAME) != ""
      STRING_TEST @Value(PLACETYPE) != ""
    PASSED -> Terminator
Terminator
    MESSAGE = Translation Terminated

FME custom transformer ENCODAGE_RRN
Ce Custom Transformer est utilisé principalement par l'équipe RRn pour traiter des caractères qui proviennent de fichiers ayant une codification autre qu UTF-8. 
À chaque fois qu'un nouveau caractère bizarre sera rencontré de façon fréquente, ce programme devra être mis à jour. 
Cette solution n'est pas la plus élégante mais c'est la plus efficace jusqu'à ce jour.

Parameters:
- SRC_ATTR = ENCODAGE   # " " Source Attribute

Note: Ce Custom transformer a été créé afin de simplifier / les mise à jour du programme principal. Lorsque de nouveaux / caractères sont rencontrés, il suffira de modifier transformer StringPairReplacer / à une seule place. / ATTENTION: il faut porter un soin particulier lorsqu'on ajoute une pair de caractères / dans ce transformer. le caractère bizarre doit conserver sa représentation originale.
StringPairReplacer_INPUT_175 (input)
    -> AttributeExposer
AttributeExposer
    ATTR_LIST = ENCODAGE
    -> StringPairReplacer
StringPairReplacer
    CASE = yes
    MAP = Ч Ç Ш È Щ É Ъ Ê Ы Ë Ю Î Я Ï д Ô й Ù л Û р à т â ч ç ш è щ é ъ ê ы ë ю î я ï є ô љ ù ћ û Ã¨ è Ã© é Ã» û Ã Î Ã´ ô Ãª ê Ã§ ç œ oe Œ OE Æ AE æ ae Ã« ë
    RESULT_ATTR = ENCODAGE
    SRC_ATTR = $(SRC_ATTR)
    -> CharacterEncoder
Note: Remplace les &nbsp; par un espace ordinaire / CHAR(160) par Char(32)
OUTPUT (output)

Bookmark: Remplace NBSP
CharacterEncoder
    CODE_VAL = 160
    STRING_ATTR = _nbsp
    -> StringReplacer_2
StringReplacer_2
    CASE = NO
    FIND_TEXT = @Value(_nbsp)
    NO_MATCH = _FME_NO_OP_
    REGEXP = NO
    REPLACE_TEXT = " "
    SRC_ATTRS = ENCODAGE
    -> StringReplacer [off]
    -> AttributeRemover
Note: Remplace les &nbsp; par / un espace ordinaire / CHAR(160) par Char(32).
AttributeRemover
    REMOVE_ATTRS = _nbsp
    -> OUTPUT (output)

Bookmark: Pour Debuggage seulement
Note: On enlève les caractères légaux
StringReplacer [off]
    CASE = YES
    FIND_TEXT = [-a-zA-Z0123456789., ôöäóéèêëàâçùûüïîÔÖÄÓÉÈÊËÀÂÇÙÛÜ Ï Î'+ /&!_'()?#: ]
    NO_MATCH = _FME_NO_OP_
    REGEXP = YES
    SRC_ATTRS = ENCODAGE
    -> Tester_2
Note: NE PAS OUBLIER D'ENLEVER LE TERMINATOR POUR COMPLÉTER LE TEST !
Tester_2 [off]
    BOOL_OP = OR
    TEST_CLAUSE = TEST @Value(ENCODAGE) != ""
    PASSED -> CharacterCodeExtractor
Note: On extrait le code des caractères illégaux pour mieux les identifier / Voir : http://ascii.cl/htmlcodes.htm
CharacterCodeExtractor [off]
    CODE_ATTR = Code_erronné
    SRC_ATTR = ENCODAGE
    -> Caractère_Erronné
Caractère_Erronné: Inspector [off]

FME custom transformer ENCODAGE
Ce Custom Transformer est utilisé principalement par l'équipe RRN pour traiter des caractères qui proviennent de fichiers ayant une codification autre queUTF-8. 
À chaque fois qu'un nouveau caractère bizarre sera rencontré, ce programme devra être mis à jour. 
Cette solution n'est pas la plus élégante mais c'est la plus efficace jusqu'à ce jour.

Parameters:
- SRC_ATTR = ENCODAGE   # " " Source Attribute

StringPairReplacer_INPUT (input)
    -> StringPairReplacer
StringPairReplacer_OUTPUT (output)

Bookmark: ENCODAGE
StringPairReplacer
    CASE = yes
    MAP = Ч Ç Ш È Щ É Ъ Ê Ы Ë Ю Î Я Ï д Ô й Ù л Û р à т â ч ç ш è щ é ъ ê ы ë ю î я ï є ô љ ù ћ û Ã¨ è Ã© é Ã» û Ã Î Ã´ ô Ãª ê Ã§ ç
    RESULT_ATTR = ENCODAGE
    SRC_ATTR = $(SRC_ATTR)
    -> StringPairReplacer_OUTPUT (output)
