FME workspace Check_Attribute_2_2018.0.fmw

Parameters:
- SourceDataset_SHAPE = E:\Work\NRN\NRN_PE_201703_deliverable\ROADSEG.shp   # Source ESRI Shape File(s)
- SourceDataset_DBF =   # Source dBASE File(s)
- DestDataset_DBF = DBF_Output   # Destination DBF File Directory
- LOG_FILE =   # Log File

Readers:
- ESRISHAPE_1: ESRISHAPE from $(SourceDataset_SHAPE)
- DBF_1: DBF from $(SourceDataset_DBF) in LLCSRS

Writers:
- DBF_2: DBF to $(DestDataset_DBF)

ADDRANGE (reader DBF_1)
    attributes: NID char(32), L_DIGDIRFG number(4,0), L_HNUMSTR number(4,0), L_RFSYSIND number(4,0), L_HNUMTYPF number(4,0), L_HNUMF number(9,0), L_HNUMSUFF char(20), L_HNUMTYPL number(4,0), L_HNUML number(9,0), L_HNUMSUFL char(20), L_OFFNANID char(32), L_ALTNANID char(32), R_DIGDIRFG number(4,0), R_HNUMSTR number(4,0), R_RFSYSIND number(4,0), R_HNUMTYPF number(4,0), R_HNUMF number(9,0), R_HNUMSUFF char(20), R_HNUMTYPL number(4,0), R_HNUML number(9,0), R_HNUMSUFL char(20), R_OFFNANID char(32), R_ALTNANID char(32), PROVIDER number(4,0), CREDATE char(10), REVDATE char(10), METACOVER number(4,0)
    -> AttributeExposer
AttributeExposer
    ATTR_LIST = fme_feature_type,NID,CREDATE,REVDATE,STRTYPRE,STARTICLE,NAMEBODY,STRTYSUF,PLACENAME,PLACETYPE,L_HNUMSUFF,L_HNUMSUFL,R_HNUMSUFF,R_HNUMSUFL,L_HNUMF,L_HNUML,R_HNUMF,R_HNUML
    -> AttributeTrimmer
AttributeTrimmer
    SRC_ATTRS = NAMEBODY,STARTICLE,R_HNUMF,L_OFFNANID,R_DIGDIRFG,L_HNUML,METACOVER,PROVIDER,R_OFFNANID,R_HNUMSUFF,STRTYPRE,CREDATE,L_HNUMTYPL,STRTYSUF,R_HNUMSTR,PLACENAME,REVDATE,L_DIGDIRFG,PLACETYPE,R_HNUMTYPF,R_RFSYSIND,R_HNUML,R_ALTNANID,L_RFSYSIND,L_ALTNANID,L_HNUMSUFF,L_HNUMSUFL,NID,L_HNUMSTR,L_HNUMTYPF,R_HNUMTYPL,L_HNUMF,R_HNUMSUFL
    TRIM_CHARS = " "
    TRIM_TO_NONE = Yes
    TRIM_TYPE = Both
    -> VallTextAttribute_2_AttributeCreator_OUTPUT_460_-__Cloner_2
VallTextAttribute_2_AttributeCreator_OUTPUT_460_-__Cloner_2: Junction
    -> DATE_2 [STRINGLENGTHCALCULATOR_7_INPUT_249]
    -> CREDATE_2 [STRINGLENGTHCALCULATOR_3_INPUT_167]
    -> REVDATE_2 [STRINGLENGTHCALCULATOR_4_INPUT_209]
    -> AttributeRenamer
    -> Matcher_2
    -> AttributeRename_4
    -> AttributeRename_2
    -> AttributeRename_5
    -> AttributeRename_6
    -> AttributeValidator_2
Note: Renommage de l'attribut L_OFFNANID pour NID
AttributeRename_2: AttributeRenamer
    ATTR_TABLE = RENAME_SET_DEFAULT L_OFFNANID > NID
    -> DuplicateFilter_2
Note: Renommage de l'attribut R_OFFNANID pour NID
AttributeRename_4: AttributeRenamer
    ATTR_TABLE = RENAME_SET_DEFAULT R_OFFNANID > NID
    -> DuplicateFilter_2
Note: Renommage de l'attribut / R_ALTNANID pour NID.
AttributeRename_6: AttributeRenamer
    ATTR_TABLE = RENAME_SET_DEFAULT R_ALTNANID > NID
    -> Tester_31
Note: Renommage de l'attribut / R_ALTNANID pour NID.
AttributeRename_5: AttributeRenamer
    ATTR_TABLE = RENAME_SET_DEFAULT L_ALTNANID > NID
    -> Tester_31
Note: Sélection des valeurs non nulles.
Tester_31
    BOOL_OP = OR
    TEST_CLAUSE = TEST @Value(NID) != -
    PASSED -> DuplicateFilter_3
Note: Élimination des enregistrements dupliqués.
DuplicateFilter_3
    INPUT_ORDERED_CHOICE = No
    KEYATTR = NID
    UNIQUE -> Matcher_5
AttributeValidator_2
    TABLE = R_DIGDIRFG,L_DIGDIRFG;RANGE;[1,3]/L_HNUMSTR,R_HNUMSTR;RANGE;[-1,4]/R_RFSYSIND,L_RFSYSIND;RANGE;[-1,5]/PROVIDER;RANGE;[1,4]/R_HNUMTYPF,L_HNUMTYPL,R_HNUMTYPL,L_HNUMTYPF;RANGE;[-1,4]/METACOVER;IN;-1,1,2/R_HNUMF,L_HNUML,L_HNUMF,R_HNUML;RANGE;[-1,]/L_OFFNANID,L_ALTNANID,R_OFFNANID,R_ALTNANID;CONTAINS_REGEX;^[0123456789abcdef]{32,32}$|^-$/NID;CONTAINS_REGEX;^[0123456789abcdef]{32,32}$
    FAILED -> Tester_17
    FAILED -> Tester_6
    FAILED -> Tester_7
    FAILED -> Tester_8
    FAILED -> Tester_12
    FAILED -> Tester_9
    FAILED -> Tester_10
    FAILED -> Tester_11
    FAILED -> Tester_13
    FAILED -> Tester_14
    FAILED -> Tester_15
    FAILED -> Tester_20
    FAILED -> Tester_22
    FAILED -> Tester_23
    FAILED -> Tester_24
    FAILED -> Tester_25
    FAILED -> Tester_4
    FAILED -> Tester_5
    FAILED -> Tester_19
    FAILED -> Tester_18
    FAILED -> Tester_16
Note: Vérification de NID.
Tester_4
    BOOL_OP = OR
    TEST_CLAUSE = TEST @Value(NID) CONTAINS_REGEX ^[0123456789abcdef]{32,32}$
    FAILED -> AttributeCreator_31
Note: AttributeCreator: / Assignation d'un commentaire d'erreur.
AttributeCreator_31
    ATTR_TABLE = SET_TO COMMENT = ATTRIBUTE: Check NID attribute for @Value(fme_feature_type)
    -> AttributeCreator_31_OUTPUT_-__OBSERVATIONS_ADDRESS
Note: Vérification de L_OFFNANID.
Tester_5
    BOOL_OP = OR
    TEST_CLAUSE:
      TEST @Value(L_OFFNANID) CONTAINS_REGEX ^[0123456789abcdef]{32,32}$
      TEST @Value(L_OFFNANID) = -
    FAILED -> AttributeCreator_2
AttributeCreator_2
    ATTR_TABLE = SET_TO COMMENT = ATTRIBUTE: Check L_OFFNANID attribute for @Value(fme_feature_type)
    -> AttributeCreator_31_OUTPUT_-__OBSERVATIONS_ADDRESS
Note: Vérification de l'attribut R_OFFNANID.
Tester_16
    BOOL_OP = OR
    TEST_CLAUSE:
      TEST @Value(R_OFFNANID) CONTAINS_REGEX ^[0123456789abcdef]{32,32}$
      TEST @Value(R_OFFNANID) = -
    FAILED -> AttributeCreator_3
AttributeCreator_3
    ATTR_TABLE = SET_TO COMMENT = ATTRIBUTE: Check R_OFFNANID attribute for @Value(fme_feature_type)
    -> AttributeCreator_31_OUTPUT_-__OBSERVATIONS_ADDRESS
Note: Vérification de l'attribut R_ALTNANID.
Tester_18
    BOOL_OP = OR
    TEST_CLAUSE:
      TEST @Value(R_ALTNANID) CONTAINS_REGEX ^[0123456789abcdef]{32,32}$
      TEST @Value(R_ALTNANID) = -
    FAILED -> AttributeCreator_4
AttributeCreator_4
    ATTR_TABLE = SET_TO COMMENT = ATTRIBUTE: Check R_ALTNANID attribute for @Value(fme_feature_type)
    -> AttributeCreator_31_OUTPUT_-__OBSERVATIONS_ADDRESS
Note: Vérification de l'attribut L_ALTNANID.
Tester_19
    BOOL_OP = OR
    TEST_CLAUSE:
      TEST @Value(L_ALTNANID) CONTAINS_REGEX ^[0123456789abcdef]{32,32}$
      TEST @Value(L_ALTNANID) = -
    FAILED -> AttributeCreator_5
AttributeCreator_5
    ATTR_TABLE = SET_TO COMMENT = ATTRIBUTE: Check L_ALTNANID attribute for @Value(fme_feature_type)
    -> AttributeCreator_31_OUTPUT_-__OBSERVATIONS_ADDRESS
Note: Vérification de l'attribut L_DIGDIRFG
Tester_17
    BOOL_OP = AND
    TEST_CLAUSE:
      TEST @Value(L_DIGDIRFG) >= 1
      TEST @Value(L_DIGDIRFG) <= 3
    FAILED -> AttributeCreator_14
AttributeCreator_14
    ATTR_TABLE = SET_TO COMMENT = ATTRIBUTE: Check L_DIGDIRFG attribute for @Value(fme_feature_type)
    -> AttributeCreator_31_OUTPUT_-__OBSERVATIONS_ADDRESS
Note: Vérification de l'attribut R_DIGDIRFG
Tester_6
    BOOL_OP = AND
    TEST_CLAUSE:
      TEST @Value(R_DIGDIRFG) >= 1
      TEST @Value(R_DIGDIRFG) <= 3
    FAILED -> AttributeCreator_15
AttributeCreator_15
    ATTR_TABLE = SET_TO COMMENT = ATTRIBUTE: Check R_DIGDIRFG attribute for @Value(fme_feature_type)
    -> AttributeCreator_31_OUTPUT_-__OBSERVATIONS_ADDRESS
Note: Vérification de l'attribut L_HNUMSTR
Tester_7
    BOOL_OP = AND
    TEST_CLAUSE:
      TEST @Value(L_HNUMSTR) >= -1
      TEST @Value(L_HNUMSTR) <= 4
    FAILED -> AttributeCreator_16
AttributeCreator_16
    ATTR_TABLE = SET_TO COMMENT = ATTRIBUTE: Check L_HNUMSTR attribute for @Value(fme_feature_type)
    -> AttributeCreator_31_OUTPUT_-__OBSERVATIONS_ADDRESS
Note: Vérification de l'attribut R_HNUMSTR
Tester_8
    BOOL_OP = AND
    TEST_CLAUSE:
      TEST @Value(R_HNUMSTR) >= -1
      TEST @Value(R_HNUMSTR) <= 4
    FAILED -> AttributeCreator_17
AttributeCreator_17
    ATTR_TABLE = SET_TO COMMENT = ATTRIBUTE: Check R_HNUMSTR attribute for @Value(fme_feature_type)
    -> AttributeCreator_31_OUTPUT_-__OBSERVATIONS_ADDRESS
Note: Vérification de l'attribut L_RFSYSIND
Tester_12
    BOOL_OP = AND
    TEST_CLAUSE:
      TEST @Value(L_RFSYSIND) >= -1
      TEST @Value(L_RFSYSIND) <= 5
    FAILED -> AttributeCreator_18
AttributeCreator_18
    ATTR_TABLE = SET_TO COMMENT = ATTRIBUTE: Check L_RFSYSIND attribute for @Value(fme_feature_type)
    -> AttributeCreator_31_OUTPUT_-__OBSERVATIONS_ADDRESS
Note: Vérification de l'attribut R_RFSYSIND
Tester_9
    BOOL_OP = AND
    TEST_CLAUSE:
      TEST @Value(R_RFSYSIND) >= -1
      TEST @Value(R_RFSYSIND) <= 5
    FAILED -> AttributeCreator_19
AttributeCreator_19
    ATTR_TABLE = SET_TO COMMENT = ATTRIBUTE: Check R_RFSYSIND attribute for @Value(fme_feature_type)
    -> AttributeCreator_31_OUTPUT_-__OBSERVATIONS_ADDRESS
Note: Vérification de l'attribut PROVIDER
Tester_10
    BOOL_OP = AND
    TEST_CLAUSE:
      TEST @Value(PROVIDER) >= 1
      TEST @Value(PROVIDER) <= 4
    FAILED -> AttributeCreator_20
AttributeCreator_20
    ATTR_TABLE = SET_TO COMMENT = ATTRIBUTE: Check PROVIDER attribute for @Value(fme_feature_type)
    -> AttributeCreator_31_OUTPUT_-__OBSERVATIONS_ADDRESS
Note: Vérification de l'attribut L_HNUMTYPF
Tester_11
    BOOL_OP = AND
    TEST_CLAUSE:
      TEST @Value(L_HNUMTYPF) >= -1
      TEST @Value(L_HNUMTYPF) <= 4
    FAILED -> AttributeCreator_21
AttributeCreator_21
    ATTR_TABLE = SET_TO COMMENT = ATTRIBUTE: Check L_HNUMTYPF attribute for @Value(fme_feature_type)
    -> AttributeCreator_31_OUTPUT_-__OBSERVATIONS_ADDRESS
Note: Vérification de l'attribut L_HNUMTYPL
Tester_13
    BOOL_OP = AND
    TEST_CLAUSE:
      TEST @Value(L_HNUMTYPL) >= -1
      TEST @Value(L_HNUMTYPL) <= 4
    FAILED -> AttributeCreator_22
AttributeCreator_22
    ATTR_TABLE = SET_TO COMMENT = ATTRIBUTE: Check L_HNUMTYPL attribute for @Value(fme_feature_type)
    -> AttributeCreator_31_OUTPUT_-__OBSERVATIONS_ADDRESS
Note: Vérification de l'attribut R_HNUMTYPF
Tester_14
    BOOL_OP = AND
    TEST_CLAUSE:
      TEST @Value(R_HNUMTYPF) >= -1
      TEST @Value(R_HNUMTYPF) <= 4
    FAILED -> AttributeCreator_23
AttributeCreator_23
    ATTR_TABLE = SET_TO COMMENT = ATTRIBUTE: Check R_HNUMTYPF attribute for @Value(fme_feature_type)
    -> AttributeCreator_31_OUTPUT_-__OBSERVATIONS_ADDRESS
Note: Vérification de l'attribut R_HNUMTYPF
Tester_15
    BOOL_OP = AND
    TEST_CLAUSE:
      TEST @Value(R_HNUMTYPF) >= -1
      TEST @Value(R_HNUMTYPF) <= 4
    FAILED -> AttributeCreator_24
AttributeCreator_24
    ATTR_TABLE = SET_TO COMMENT = ATTRIBUTE: Check R_HNUMTYPL attribute for @Value(fme_feature_type)
    -> AttributeCreator_31_OUTPUT_-__OBSERVATIONS_ADDRESS
Note: Vérification de l'attribut METACOVER
Tester_20
    BOOL_OP = OR
    TEST_CLAUSE:
      TEST @Value(METACOVER) = -1
      TEST @Value(METACOVER) = 1
      TEST @Value(METACOVER) = 2
    FAILED -> AttributeCreator_25
AttributeCreator_25
    ATTR_TABLE = SET_TO COMMENT = ATTRIBUTE: Check METACOVER attribute for @Value(fme_feature_type)
    -> AttributeCreator_31_OUTPUT_-__OBSERVATIONS_ADDRESS
Note: Vérification de l'attribut
Tester_22
    BOOL_OP = OR
    TEST_CLAUSE = TEST @Value(L_HNUMF) >= -1
    FAILED -> AttributeCreator_26
AttributeCreator_26
    ATTR_TABLE = SET_TO COMMENT = ATTRIBUTE: Check L_HNUMF attribute for @Value(fme_feature_type)
    -> AttributeCreator_31_OUTPUT_-__OBSERVATIONS_ADDRESS
Note: Vérification de l'attribut L_HNUML
Tester_23
    BOOL_OP = OR
    TEST_CLAUSE = TEST @Value(L_HNUML) >= -1
    FAILED -> AttributeCreator_27
AttributeCreator_27
    ATTR_TABLE = SET_TO COMMENT = ATTRIBUTE: Check L_HNUML attribute for @Value(fme_feature_type)
    -> AttributeCreator_31_OUTPUT_-__OBSERVATIONS_ADDRESS
Note: Vérification de l'attribut R_HNUMF
Tester_24
    BOOL_OP = OR
    TEST_CLAUSE = TEST @Value(R_HNUMF) >= -1
    FAILED -> AttributeCreator_28
AttributeCreator_28
    ATTR_TABLE = SET_TO COMMENT = ATTRIBUTE: Check R_HNUMF attribute for @Value(fme_feature_type)
    -> AttributeCreator_31_OUTPUT_-__OBSERVATIONS_ADDRESS
Note: Vérification de l'attribut R_HNUML
Tester_25
    BOOL_OP = OR
    TEST_CLAUSE = TEST @Value(R_HNUML) >= -1
    FAILED -> AttributeCreator_29
AttributeCreator_29
    ATTR_TABLE = SET_TO COMMENT = ATTRIBUTE: Check R_HNUML attribute for @Value(fme_feature_type)
    -> AttributeCreator_31_OUTPUT_-__OBSERVATIONS_ADDRESS
AttributeCreator_31_OUTPUT_-__OBSERVATIONS_ADDRESS: Junction
    -> OBSERVATIONS_ADDRESS (writer DBF_2)
Note: Renommage de l'attribut NID pour ADRANGENID.
AttributeRenamer
    ATTR_TABLE = RENAME_SET_DEFAULT NID > ADRANGENID
    -> Matcher_3
Note: Match sur NID
Matcher_2
    BLANK_AND_MISSING_DIFFER = No
    CNT_ATTR = _match_id
    LENIENT_MATCH = No
    MATCH = NONE
    MATCHATTRS = NID
    MATCH_STRATEGY = Match Selected Attributes
    MATCHED -> AttributeCreator_30
Note: Assignation d'un commentaire d'erreur.
AttributeCreator_30
    ATTR_TABLE = SET_TO COMMENT = ATTRIBUTE: Duplicated NID attribute
    -> OBSERVATIONS_ADDRESS (writer DBF_2)
Note: Vérification de l'attribut CREDATE.
CREDATE_2
    Cloner_COPY_878 -> OBSERVATIONS_ADDRESS (writer DBF_2)
Note: Vérification de l'attribut REVDATE.
REVDATE_2
    Cloner_COPY_751 -> OBSERVATIONS_ADDRESS (writer DBF_2)
Note: Vérification si le REVDATE est plus grand ou égal au CREDATE.
DATE_2
    ATTRIBUTECREATOR_61_OUTPUT_262 -> OBSERVATIONS_ADDRESS (writer DBF_2)
STRPLANAME (reader DBF_1)
    attributes: NID char(32), DIRPREFIX number(4,0), STRTYPRE char(30), STARTICLE char(20), NAMEBODY char(50), STRTYSUF char(30), DIRSUFFIX number(4,0), MUNIQUAD number(4,0), PLACENAME char(100), PROVINCE number(4,0), PLACETYPE char(100), PROVIDER number(4,0), CREDATE char(10), REVDATE char(10)
    -> AttributeExposer_3
AttributeExposer_3
    ATTR_LIST = fme_feature_type
    -> AttributeTrimmer_3
AttributeTrimmer_3
    SRC_ATTRS = DIRSUFFIX,NAMEBODY,CREDATE,NID,STRTYPRE,PLACETYPE,PROVINCE,STRTYSUF,PLACENAME,STARTICLE,MUNIQUAD,DIRPREFIX,PROVIDER,REVDATE
    TRIM_CHARS = " "
    TRIM_TO_NONE = Yes
    TRIM_TYPE = Both
    -> VallTextAttribute_3_Tester_OUTPUT_2_-__Cloner
VallTextAttribute_3_Tester_OUTPUT_2_-__Cloner: Junction
    -> AttributeValidator
    -> Matcher
    -> CREDATE [STRINGLENGTHCALCULATOR_3_INPUT_167]
    -> REVDATE [STRINGLENGTHCALCULATOR_4_INPUT_209]
    -> DATE [STRINGLENGTHCALCULATOR_7_INPUT_249]
    -> Matcher_4
Note: Version de compilation : 5206 / --REVISION-- $Id: check_attribute_2_v2.fmw 3421 2016-11-21 14:29:16Z rbrisson $
Note: Nom du workbench : check_attribute_2_v2 / Auteur : Denis Bergeron / Date de création : 12-octo-2006 / Description : Vérification des domaines de valeurs des attributs / et des liens entre les tables d'adresse.
AttributeValidator
    TABLE = NID;CONTAINS_REGEX;^[0123456789abcdef]{32,32}$/DIRPREFIX;RANGE;[0,18]/PROVIDER;RANGE;[1,4]/PROVINCE;RANGE;[1,13]/MUNIQUAD;RANGE;[0,4]/DIRSUFFIX;RANGE;[0,18]
    FAILED -> Tester
    FAILED -> Tester_26
    FAILED -> Tester_30
    FAILED -> Tester_29
    FAILED -> Tester_28
    FAILED -> Tester_27
Note: Vérification de l'attribut NID.
Tester
    BOOL_OP = OR
    TEST_CLAUSE = TEST @Value(NID) CONTAINS_REGEX ^[0123456789abcdef]{32,32}$
    FAILED -> AttributeCreator
Note: AttributeCreator: / Assignation d'un commentaire d'erreur.
AttributeCreator
    ATTR_TABLE = SET_TO COMMENT = ATTRIBUTE: Check NID attribute for @Value(fme_feature_type)
    -> ATTRIBUTECREATOR_2_OUTPUT_-__OBSERVATIONS_STREET
Note: Vérification de l'attribut DIRPREFIX
Tester_26
    BOOL_OP = AND
    TEST_CLAUSE:
      TEST @Value(DIRPREFIX) >= 0
      TEST @Value(DIRPREFIX) <= 18
    FAILED -> AttributeCreator_9
AttributeCreator_9
    ATTR_TABLE = SET_TO COMMENT = ATTRIBUTE: Check DIRPREFIX attribute for @Value(fme_feature_type)
    -> ATTRIBUTECREATOR_2_OUTPUT_-__OBSERVATIONS_STREET
Note: Vérification de l'attribut PROVIDER
Tester_30
    BOOL_OP = AND
    TEST_CLAUSE:
      TEST @Value(PROVIDER) >= 1
      TEST @Value(PROVIDER) <= 4
    FAILED -> AttributeCreator_10
AttributeCreator_10
    ATTR_TABLE = SET_TO COMMENT = ATTRIBUTE: Check PROVIDER attribute for @Value(fme_feature_type)
    -> ATTRIBUTECREATOR_2_OUTPUT_-__OBSERVATIONS_STREET
Note: Vérification de l'attribut PROVINCE
Tester_29
    BOOL_OP = AND
    TEST_CLAUSE:
      TEST @Value(PROVINCE) >= 1
      TEST @Value(PROVINCE) <= 13
    FAILED -> AttributeCreator_11
AttributeCreator_11
    ATTR_TABLE = SET_TO COMMENT = ATTRIBUTE: Check PROVINCE attribute for @Value(fme_feature_type)
    -> ATTRIBUTECREATOR_2_OUTPUT_-__OBSERVATIONS_STREET
Note: Vérification de l'attribut MUNIQUAD
Tester_28
    BOOL_OP = AND
    TEST_CLAUSE:
      TEST @Value(MUNIQUAD) >= 0
      TEST @Value(MUNIQUAD) <= 4
    FAILED -> AttributeCreator_12
AttributeCreator_12
    ATTR_TABLE = SET_TO COMMENT = ATTRIBUTE: Check MUNIQUAD attribute for @Value(fme_feature_type)
    -> ATTRIBUTECREATOR_2_OUTPUT_-__OBSERVATIONS_STREET
Note: Vérification de l'attribut DIRSUFFIX
Tester_27
    BOOL_OP = AND
    TEST_CLAUSE:
      TEST @Value(DIRSUFFIX) >= 0
      TEST @Value(DIRSUFFIX) <= 18
    FAILED -> AttributeCreator_13
AttributeCreator_13
    ATTR_TABLE = SET_TO COMMENT = ATTRIBUTE: Check DIRSUFFIX attribute for @Value(fme_feature_type)
    -> ATTRIBUTECREATOR_2_OUTPUT_-__OBSERVATIONS_STREET
Note: Match des NID
Matcher
    BLANK_AND_MISSING_DIFFER = No
    CNT_ATTR = _match_id
    LENIENT_MATCH = No
    MATCH = NONE
    MATCHATTRS = NID
    MATCH_STRATEGY = Match Selected Attributes
    MATCHED -> AttributeCreator_8
AttributeCreator_8
    ATTR_TABLE = SET_TO COMMENT = ATTRIBUTE: Duplicated NID attribute
    -> ATTRIBUTECREATOR_2_OUTPUT_-__OBSERVATIONS_STREET
Note: Vérification de l'attribut CREDATE.
CREDATE
    Cloner_COPY_878 -> ATTRIBUTECREATOR_2_OUTPUT_-__OBSERVATIONS_STREET
Note: Vérification de l'attribut REVDATE.
REVDATE
    Cloner_COPY_751 -> ATTRIBUTECREATOR_2_OUTPUT_-__OBSERVATIONS_STREET
Note: Vérification si le REVDATE est plus grand ou égal au CREDATE.
DATE
    ATTRIBUTECREATOR_61_OUTPUT_262 -> ATTRIBUTECREATOR_2_OUTPUT_-__OBSERVATIONS_STREET
ATTRIBUTECREATOR_2_OUTPUT_-__OBSERVATIONS_STREET: Junction
    -> OBSERVATIONS_STREET (writer DBF_2)
ROADSEG (reader ESRISHAPE_1)
    attributes: NID char(32), ROADSEGID number(9,0), ADRANGENID char(32), DATASETNAM number(4,0), ACQTECH number(4,0), ACCURACY number(4,0), PROVIDER number(4,0), CREDATE char(10), REVDATE char(10), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0), STRUCTID char(32),
      STRUCTTYPE number(4,0), STRUNAMEEN char(100), STRUNAMEFR char(100)
    -> AttributeTrimmer_4
AttributeTrimmer_4
    SRC_ATTRS = RTENAME2EN,EXITNBR,METACOVER,PROVIDER,RTENAME4EN,RTENAME1EN,CREDATE,RTNUMBER3,NBRLANES,UNPAVSURF,PAVSURF,REVDATE,RTENAME3FR,RTNUMBER2,ACCURACY,RTNUMBER1,STRUNAMEEN,ROADCLASS,STRUCTTYPE,RTENAME3EN,DATASETNAM,NID,PAVSTATUS,RTENAME4FR,ADRANGENID,STRUCTID,RTENAME1FR,RTNUMBER4,RTNUMBER5,ROADSEGID,RTENAME2FR,ACQTECH,STRUNAMEFR
    TRIM_CHARS = " "
    TRIM_TO_NONE = Yes
    TRIM_TYPE = Both
    -> DuplicateFilter
Note: Élimination des enregistrements dupliqués.
DuplicateFilter
    INPUT_ORDERED_CHOICE = No
    KEYATTR = ADRANGENID
    UNIQUE -> Matcher_3
Note: Vérification des liens entre les tables ROADSEG et ADDRANGE.
Matcher_3
    BLANK_AND_MISSING_DIFFER = No
    CNT_ATTR = _match_id
    DIFFATTRS = fme_feature_type
    LENIENT_MATCH = No
    MATCH = NONE
    MATCHATTRS = ADRANGENID
    MATCH_STRATEGY = Match Selected Attributes
    NOT_MATCHED -> AttributeRename_7
Note: Renommage de l'attribut / ADRANGENID pour NID.
AttributeRename_7: AttributeRenamer
    ATTR_TABLE = RENAME_SET_DEFAULT ADRANGENID > NID
    -> Tester_45
Note: Sélection des valeurs non nulles.
Tester_45
    BOOL_OP = OR
    TEST_CLAUSE = TEST @Value(NID) != -
    PASSED -> AttributeCreator_32
Note: Assignation d'un commentaire d'erreur.
AttributeCreator_32
    ATTR_TABLE = SET_TO COMMENT = ATTRIBUTE: Unlinked NID attribute
    -> OBSERVATIONS_ADDRESS (writer DBF_2)
ALTNAMLINK (reader DBF_1)
    attributes: NID char(32), STRNAMENID char(32), CREDATE char(10), REVDATE char(10)
    -> AttributeTrimmer_2
AttributeTrimmer_2
    SRC_ATTRS = STRNAMENID,CREDATE,NID,REVDATE
    TRIM_CHARS = " "
    TRIM_TO_NONE = Yes
    TRIM_TYPE = Both
    -> DuplicateFilter_4
    -> REVDATE_3 [STRINGLENGTHCALCULATOR_4_INPUT_209]
    -> CREDATE_3 [STRINGLENGTHCALCULATOR_3_INPUT_167]
    -> AttributeValidator_3
    -> DATE_3 [STRINGLENGTHCALCULATOR_7_INPUT_249]
    -> AttributeRename_3
Note: Renommage de l'attribut STRNAMENID pour NID
AttributeRename_3: AttributeRenamer
    ATTR_TABLE = RENAME_SET_DEFAULT STRNAMENID > NID
    -> DuplicateFilter_2
Note: Élimination des enregistrements dupliqués.
DuplicateFilter_2
    INPUT_ORDERED_CHOICE = No
    KEYATTR = NID
    UNIQUE -> Matcher_4
Note: Vérification des liens entre les tables / ADDRANGE, / ALTNAMLINK / et STRPLANAME
Matcher_4
    BLANK_AND_MISSING_DIFFER = No
    CNT_ATTR = _match_id
    DIFFATTRS = fme_feature_type
    LENIENT_MATCH = No
    MATCH = NONE
    MATCHATTRS = NID
    MATCH_STRATEGY = Match Selected Attributes
    NOT_MATCHED -> TestFilter
Note: Identification de la table.
TestFilter
    DEFAULT_VALUE = <UNFILTERED>
    TEST_LIST = BOOL_OP,OR,COMPOSITE_TEST,<Unused>,TEST_CLAUSE,"TEST @Value(fme_feature_type) = STRPLANAME",STRPLANAME,BOOL_OP,OR,COMPOSITE_TEST,<Unused>,TEST_CLAUSE,"TEST @Value(fme_feature_type) = ADDRANGE",ADDRANGE,BOOL_OP,OR,COMPOSITE_TEST,<Unused>,TEST_CLAUSE,"TEST @Value(fme_feature_type) = ALTNAMLINK",ALTNAMLINK
    STRPLANAME -> AttributeCreator_34
    ADDRANGE -> Tester_46
    ALTNAMLINK -> AttributeCreator_36
Note: Assignation d'un commentaire d'erreur.
AttributeCreator_34
    ATTR_TABLE = SET_TO COMMENT = ATTRIBUTE: Unlinked NID attribute
    -> OBSERVATIONS_STREET (writer DBF_2)
OBSERVATIONS_STREET (writer DBF_2)
    attributes: NID char(32), COMMENT char(50)
Note: Sélection des valeurs non nulles.
Tester_46
    BOOL_OP = OR
    TEST_CLAUSE = TEST @Value(NID) != -
    PASSED -> AttributeCreator_35
Note: Assignation d'un commentaire d'erreur.
AttributeCreator_35
    ATTR_TABLE = SET_TO COMMENT = ATTRIBUTE: Unlinked NID attribute
    -> OBSERVATIONS_ADDRESS (writer DBF_2)
Note: Assignation d'un commentaire d'erreur.
AttributeCreator_36
    ATTR_TABLE = SET_TO COMMENT = ATTRIBUTE: Unlinked NID attribute
    -> OBSERVATIONS_ALTERNATE (writer DBF_2)
Note: Élimination des enregistrements dupliqués.
DuplicateFilter_4
    INPUT_ORDERED_CHOICE = No
    KEYATTR = NID
    UNIQUE -> Matcher_5
Note: Vérification des liens entre les tables / ADDRANGE et / ALTNAMLINK
Matcher_5
    BLANK_AND_MISSING_DIFFER = No
    CNT_ATTR = _match_id
    DIFFATTRS = fme_feature_type
    LENIENT_MATCH = No
    MATCH = NONE
    MATCHATTRS = NID
    MATCH_STRATEGY = Match Selected Attributes
    NOT_MATCHED -> TestFilter_2
Note: Identification de la table.
TestFilter_2
    DEFAULT_VALUE = <UNFILTERED>
    TEST_LIST = BOOL_OP,OR,COMPOSITE_TEST,<Unused>,TEST_CLAUSE,"TEST @Value(fme_feature_type) = ADDRANGE",ADDRANGE,BOOL_OP,OR,COMPOSITE_TEST,<Unused>,TEST_CLAUSE,"TEST @Value(fme_feature_type) = ALTNAMLINK",ALTNAMLINK
    ADDRANGE -> AttributeCreator_33
    ALTNAMLINK -> AttributeCreator_37
Note: Assignation d'un commentaire d'erreur.
AttributeCreator_33
    ATTR_TABLE = SET_TO COMMENT = ATTRIBUTE: Unlinked NID attribute
    -> OBSERVATIONS_ADDRESS (writer DBF_2)
OBSERVATIONS_ADDRESS (writer DBF_2)
    attributes: NID char(32), COMMENT char(50)
Note: Assignation d'un commentaire d'erreur.
AttributeCreator_37
    ATTR_TABLE = SET_TO COMMENT = ATTRIBUTE: Unlinked NID attribute
    -> OBSERVATIONS_ALTERNATE (writer DBF_2)
AttributeValidator_3
    TABLE = STRNAMENID,NID;CONTAINS_REGEX;^[0123456789abcdef]{32,32}$
    FAILED -> Tester_2
    FAILED -> Tester_3
Note: Vérification de l'attribut NID.
Tester_2
    BOOL_OP = OR
    TEST_CLAUSE = TEST @Value(NID) CONTAINS_REGEX ^[0123456789abcdef]{32,32}$
    FAILED -> AttributeCreator_6
Note: Assignation d'un commentaire d'erreur.
AttributeCreator_6
    ATTR_TABLE = SET_TO COMMENT = ATTRIBUTE: Check NID attribute
    -> ATTRIBUTECREATOR_8_OUTPUT_-__OBSERVATIONS_ALTERNATE
Note: Vérification de l'attribut STRNAMENID.
Tester_3
    BOOL_OP = OR
    TEST_CLAUSE = TEST @Value(STRNAMENID) CONTAINS_REGEX ^[0123456789abcdef]{32,32}$
    FAILED -> AttributeCreator_7
Note: Assignation d'un commentaire d'erreur.
AttributeCreator_7
    ATTR_TABLE = SET_TO COMMENT = ATTRIBUTE: Check STRNAMENID attribute
    -> ATTRIBUTECREATOR_8_OUTPUT_-__OBSERVATIONS_ALTERNATE
Note: Vérification de l'attribut CREDATE.
CREDATE_3
    Cloner_COPY_878 -> ATTRIBUTECREATOR_8_OUTPUT_-__OBSERVATIONS_ALTERNATE
Note: Vérification de l'attribut REVDATE.
REVDATE_3
    Cloner_COPY_751 -> ATTRIBUTECREATOR_8_OUTPUT_-__OBSERVATIONS_ALTERNATE
Note: Vérification si le REVDATE est plus grand ou égal au CREDATE.
DATE_3
    ATTRIBUTECREATOR_61_OUTPUT_262 -> ATTRIBUTECREATOR_8_OUTPUT_-__OBSERVATIONS_ALTERNATE
ATTRIBUTECREATOR_8_OUTPUT_-__OBSERVATIONS_ALTERNATE: Junction
    -> OBSERVATIONS_ALTERNATE (writer DBF_2)
OBSERVATIONS_ALTERNATE (writer DBF_2)
    attributes: NID char(32), COMMENT char(50)

FME custom transformer DATE
Vérification si le REVDATE est plus grand ou égal au CREDATE.

STRINGLENGTHCALCULATOR_7_INPUT_249 (input)
    -> AttributeExposer
Note: Exposition des attributs CREDATE et REVDATE.
AttributeExposer
    ATTR_LIST = CREDATE,REVDATE,fme_feature_type
    -> TestFilter
Note: Validation de la longueur de l'attribut CREDATE et REVDATE. / On s'attend à des éléments <Unfiltered>.
TestFilter
    DEFAULT_VALUE = <UNFILTERED>
    TEST_LIST:
      BOOL_OP,AND,COMPOSITE_TEST,<Unused>,TEST_CLAUSE,"TEST @Value(CREDATE) CONTAINS_REGEX ^[0123456789]{4,4}$
      TEST @Value(REVDATE) CONTAINS_REGEX ^[0123456789]{4,4}$",Cre4Rev4,BOOL_OP,AND,COMPOSITE_TEST,<Unused>,TEST_CLAUSE,"TEST @Value(CREDATE) CONTAINS_REGEX ^[0123456789]{6,6}$
      TEST @Value(REVDATE) CONTAINS_REGEX ^[0123456789]{6,6}$",Cre6Rev6,BOOL_OP,AND,COMPOSITE_TEST,<Unused>,TEST_CLAUSE,"TEST @Value(CREDATE) CONTAINS_REGEX ^[0123456789]{8,8}$
      TEST @Value(REVDATE) CONTAINS_REGEX ^[0123456789]{8,8}$",Cre8Rev8,BOOL_OP,AND,COMPOSITE_TEST,<Unused>,TEST_CLAUSE,"TEST @Value(CREDATE) CONTAINS_REGEX ^[0123456789]{4,4}$
      TEST @Value(REVDATE) CONTAINS_REGEX ^[0123456789]{6,6}$",Cre4Rev6,BOOL_OP,AND,COMPOSITE_TEST,<Unused>,TEST_CLAUSE,"TEST @Value(CREDATE) CONTAINS_REGEX ^[0123456789]{4,4}$
      TEST @Value(REVDATE) CONTAINS_REGEX ^[0123456789]{8,8}$",Cre4Rev8,BOOL_OP,AND,COMPOSITE_TEST,<Unused>,TEST_CLAUSE,"TEST @Value(CREDATE) CONTAINS_REGEX ^[0123456789]{6,6}$
      TEST @Value(REVDATE) CONTAINS_REGEX ^[0123456789]{8,8}$",Cre6Rev8,BOOL_OP,AND,COMPOSITE_TEST,<Unused>,TEST_CLAUSE,"TEST @Value(CREDATE) CONTAINS_REGEX ^[0123456789]{4,4}$
      TEST @Value(REVDATE) CONTAINS_REGEX ^[0123456789]{6,6}$",Cre6Rev4,BOOL_OP,AND,COMPOSITE_TEST,<Unused>,TEST_CLAUSE,"TEST @Value(CREDATE) CONTAINS_REGEX ^[0123456789]{4,4}$
      TEST @Value(REVDATE) CONTAINS_REGEX ^[0123456789]{8,8}$",Cre8Rev4,BOOL_OP,AND,COMPOSITE_TEST,<Unused>,TEST_CLAUSE,"TEST @Value(CREDATE) CONTAINS_REGEX ^[0123456789]{6,6}$
      TEST @Value(REVDATE) CONTAINS_REGEX ^[0123456789]{8,8}$",Cre8Rev6,BOOL_OP,OR,COMPOSITE_TEST,<Unused>,TEST_CLAUSE,"TEST @Value(CREDATE) CONTAINS_REGEX ^[0123456789]{8,8}$
      TEST @Value(CREDATE) CONTAINS_REGEX ^[0123456789]{6,6}$
      TEST @Value(CREDATE) CONTAINS_REGEX ^[0123456789]{4,4}$",REV invalide,BOOL_OP,OR,COMPOSITE_TEST,<Unused>,TEST_CLAUSE,"TEST @Value(REVDATE) CONTAINS_REGEX ^[0123456789]{8,8}$
      TEST @Value(REVDATE) CONTAINS_REGEX ^[0123456789]{6,6}$
      TEST @Value(REVDATE) CONTAINS_REGEX ^[0123456789]{4,4}$",CRE invalide
    Cre4Rev4 -> Tester
    Cre6Rev6 -> Tester
    Cre8Rev8 -> Tester
    Cre4Rev6 -> StringConcatenator
    Cre4Rev8 -> StringConcatenator_3
    Cre6Rev8 -> StringConcatenator_4
    Cre6Rev4 -> StringConcatenator_5
    Cre8Rev4 -> StringConcatenator_7
    Cre8Rev6 -> StringConcatenator_8
    REV invalide -> AttributeCreator_2
    CRE invalide -> AttributeCreator_4
    <UNFILTERED> -> AttributeCreator_3
AttributeCreator_2
    ATTR_TABLE = SET_TO COMMENT = ATTRIBUTE: Check REVDATE attribute value for @Value(fme_feature_type)
    -> ATTRIBUTECREATOR_61_OUTPUT_262 (output)
Note: StringConcatenator: / Concaténation pour avoir une date dans un format YYYYMMDD
StringConcatenator
    ACTION = Create New Attribute
    PARM_LINE = @Value(CREDATE)0101
    VAL_ATTR = CREDATE
    -> StringConcatenator_2
StringConcatenator_2
    ACTION = Create New Attribute
    PARM_LINE = @Value(REVDATE)01
    VAL_ATTR = REVDATE
    -> Tester
AttributeCreator_4
    ATTR_TABLE = SET_TO COMMENT = ATTRIBUTE: Check CREDATE attribute value for @Value(fme_feature_type)
    -> ATTRIBUTECREATOR_61_OUTPUT_262 (output)
StringConcatenator_3
    ACTION = Create New Attribute
    PARM_LINE = @Value(CREDATE)0101
    VAL_ATTR = CREDATE
    -> Tester
AttributeCreator_3
    ATTR_TABLE = SET_TO COMMENT = ATTRIBUTE: Check REVDATE attribute value and CREDATE attribute value for @Value(fme_feature_type)
    -> ATTRIBUTECREATOR_61_OUTPUT_262 (output)
StringConcatenator_4
    ACTION = Create New Attribute
    PARM_LINE = @Value(CREDATE)01
    VAL_ATTR = CREDATE
    -> Tester
StringConcatenator_5
    ACTION = Create New Attribute
    PARM_LINE = @Value(CREDATE)01
    VAL_ATTR = CREDATE
    -> StringConcatenator_6
StringConcatenator_6
    ACTION = Create New Attribute
    PARM_LINE = @Value(REVDATE)0101
    VAL_ATTR = REVDATE
    -> Tester
StringConcatenator_7
    ACTION = Create New Attribute
    PARM_LINE = @Value(REVDATE)0101
    VAL_ATTR = REVDATE
    -> Tester
StringConcatenator_8
    ACTION = Create New Attribute
    PARM_LINE = @Value(REVDATE)01
    VAL_ATTR = REVDATE
    -> Tester
Note: Vérification de la validité des dates. / On s'attend à des éléments <Passed>.
Tester
    BOOL_OP = COMPOSITE
    COMPOSITE_TEST = "1 OR (2 AND 3)"
    TEST_CLAUSE = TEST @Value(CREDATE) <= @Value(REVDATE)
    FAILED -> AttributeCreator_61
Note: AttributeCreator: / Assignation d'un commentaire d'erreur.
AttributeCreator_61
    ATTR_TABLE = SET_TO COMMENT = ATTRIBUTE: Check validity of REVDATE attribute for @Value(fme_feature_type)
    -> ATTRIBUTECREATOR_61_OUTPUT_262 (output)
ATTRIBUTECREATOR_61_OUTPUT_262 (output)

FME custom transformer REVDATE
Vérification de l'attribut REVDATE.

STRINGLENGTHCALCULATOR_4_INPUT_209 (input)
    -> AttributeExposer
Note: Exposition des attributs REVDATE et FME_FEATURE_TYPE.
AttributeExposer
    ATTR_LIST = REVDATE,fme_feature_type
    -> Tester_2
Note: Retirer de la validation les données ayant une valeur null pour l'attribut REVDATE. / On s'attend à des éléments <Failed>.
Tester_2
    BOOL_OP = OR
    TEST_CLAUSE = TEST @Value(REVDATE) ATTRIBUTE_HAS_VALUE ""
    PASSED -> TimeStamper_2
Note: TimeStamper: Extraction de l'année, du mois et/ou du jours actuels.
TimeStamper_2
    FMT = ^Y^m^d
    TIME_ATTR = _timestamp_day
    -> TimeStamper_3
TimeStamper_3
    FMT = ^Y^m
    TIME_ATTR = _timestamp_month
    -> TimeStamper_4
TimeStamper_4
    FMT = ^Y
    TIME_ATTR = _timestamp_year
    -> TestFilter
Note: Trie selon la longueur de l'attribut REVDATE (YYYY, YYYYMM ou YYYYMMDD).
Note: DataFormatter: / Extraction du jour, du mois ou de l'année.
Note: TestFilter: / Test contraintes de date / On s'attend à des éléments <Unfiltered>.
TestFilter
    DEFAULT_VALUE = <UNFILTERED>
    TEST_LIST = BOOL_OP,AND,COMPOSITE_TEST,<Unused>,TEST_CLAUSE,"TEST @Value(REVDATE) CONTAINS_REGEX ^[0123456789]{4,4}$",REV4,BOOL_OP,AND,COMPOSITE_TEST,<Unused>,TEST_CLAUSE,"TEST @Value(REVDATE) CONTAINS_REGEX ^[0123456789]{6,6}$",REV6,BOOL_OP,AND,COMPOSITE_TEST,<Unused>,TEST_CLAUSE,"TEST @Value(REVDATE) CONTAINS_REGEX ^[0123456789]{8,8}$",REV8
    REV4 -> TestFilter_5
    REV6 -> SubstringExtractor_4
    REV6 -> SubstringExtractor_7
    REV8 -> SubstringExtractor_8
    REV8 -> SubstringExtractor_6
    REV8 -> SubstringExtractor_5
    <UNFILTERED> -> AttributeCreator_2
Note: AttributeCreator: Assignation d'un commentaire d'erreur.
Cloner_COPY_751 (output)

Bookmark: Year
SubstringExtractor_4
    END = 3
    RESULT_ATTR = REVDATE
    SRC_STRING = @Value(REVDATE)
    START = 0
    -> TestFilter_5
SubstringExtractor_5
    END = 3
    RESULT_ATTR = REVDATE
    SRC_STRING = @Value(REVDATE)
    START = 0
    -> TestFilter_5
TestFilter_5
    DEFAULT_VALUE = <UNFILTERED>
    TEST_LIST = BOOL_OP,AND,COMPOSITE_TEST,<Unused>,TEST_CLAUSE,"TEST @Value(REVDATE) NOT_>= 1960",1960,BOOL_OP,AND,COMPOSITE_TEST,<Unused>,TEST_CLAUSE,"TEST @Value(REVDATE) NOT_<= @Value(_timestamp_year)",timestamp
    1960 -> AttributeCreator_10
    timestamp -> AttributeCreator_14
AttributeCreator_10
    ATTR_TABLE = SET_TO COMMENT = ATTRIBUTE: Check year of REVDATE attribute for @Value(fme_feature_type)
    -> Cloner_COPY_751 (output)
AttributeCreator_14
    ATTR_TABLE = SET_TO COMMENT = ATTRIBUTE: Check REVDATE attribute for @Value(fme_feature_type)
    -> Cloner_COPY_751 (output)

Bookmark: Month
SubstringExtractor_6
    END = 5
    RESULT_ATTR = REVDATE
    SRC_STRING = @Value(REVDATE)
    START = 4
    -> TestFilter_6
SubstringExtractor_7
    END = 5
    RESULT_ATTR = REVDATE
    SRC_STRING = @Value(REVDATE)
    START = 4
    -> TestFilter_6
TestFilter_6
    DEFAULT_VALUE = <UNFILTERED>
    TEST_LIST:
      BOOL_OP,AND,COMPOSITE_TEST,<Unused>,TEST_CLAUSE,"TEST @Value(REVDATE) NOT_>= 01
      TEST @Value(REVDATE) NOT_<= 12",month_01_12,BOOL_OP,AND,COMPOSITE_TEST,<Unused>,TEST_CLAUSE,"TEST @Value(REVDATE) NOT_<= @Value(_timestamp_month)",timestamp
    month_01_12 -> AttributeCreator_11
    timestamp -> AttributeCreator_9
AttributeCreator_11
    ATTR_TABLE = SET_TO COMMENT = ATTRIBUTE: Check month of REVDATE attribute for @Value(fme_feature_type)
    -> Cloner_COPY_751 (output)
AttributeCreator_9
    ATTR_TABLE = SET_TO COMMENT = ATTRIBUTE: Check REVDATE attribute for @Value(fme_feature_type)
    -> Cloner_COPY_751 (output)

Bookmark: Day
SubstringExtractor_8
    END = 7
    RESULT_ATTR = REVDATE
    SRC_STRING = @Value(REVDATE)
    START = 6
    -> TestFilter_7
TestFilter_7
    DEFAULT_VALUE = <UNFILTERED>
    TEST_LIST:
      BOOL_OP,AND,COMPOSITE_TEST,<Unused>,TEST_CLAUSE,"TEST @Value(REVDATE) NOT_>= 01
      TEST @Value(REVDATE) NOT_<= 31",day_01_31,BOOL_OP,AND,COMPOSITE_TEST,<Unused>,TEST_CLAUSE,"TEST @Value(REVDATE) NOT_<= @Value(_timestamp_day)",timestamp
    day_01_31 -> AttributeCreator_12
    timestamp -> AttributeCreator_13
AttributeCreator_12
    ATTR_TABLE = SET_TO COMMENT = ATTRIBUTE: Check day of REVDATE attribute for @Value(fme_feature_type)
    -> Cloner_COPY_751 (output)
AttributeCreator_13
    ATTR_TABLE = SET_TO COMMENT = ATTRIBUTE: Check REVDATE attribute for @Value(fme_feature_type)
    -> Cloner_COPY_751 (output)
AttributeCreator_2
    ATTR_TABLE = SET_TO COMMENT = ATTRIBUTE: Check length of REVDATE attribute for @Value(fme_feature_type)
    -> Cloner_COPY_751 (output)

FME custom transformer CREDATE
Vérification de l'attribut CREDATE.

STRINGLENGTHCALCULATOR_3_INPUT_167 (input)
    -> AttributeExposer_2
Note: Exposition des attributs CREDATE et FME_FEATURE_TYPE.
AttributeExposer_2
    ATTR_LIST = CREDATE,fme_feature_type
    -> Tester_4
Note: Retirer de la validation les données ayant une valeur null pour l'attribut CREDATE. / On s'attend à des éléments <Failed>.
Tester_4
    BOOL_OP = OR
    TEST_CLAUSE = TEST @Value(CREDATE) ATTRIBUTE_HAS_VALUE ""
    PASSED -> TimeStamper_2
Note: TimeStamper: Extraction de l'année, du mois et/ou du jours actuels.
TimeStamper_2
    FMT = ^Y^m^d
    TIME_ATTR = _timestamp_day
    -> TimeStamper_3
TimeStamper_3
    FMT = ^Y^m
    TIME_ATTR = _timestamp_month
    -> TimeStamper_7
TimeStamper_7
    FMT = ^Y
    TIME_ATTR = _timestamp_year
    -> TestFilter
Note: Trie selon la longueur de l'attribut CREDATE. / (YYYY, YYYYMM ou YYYYMMDD)
Note: DataFormatter: / Extraction du jour, du mois ou de l'année.
Note: TestFilter: / Test contraintes de date / On s'attend à des élléments <Unfiltered>.
TestFilter
    DEFAULT_VALUE = <UNFILTERED>
    TEST_LIST = BOOL_OP,AND,COMPOSITE_TEST,<Unused>,TEST_CLAUSE,"TEST @Value(CREDATE) CONTAINS_REGEX ^[0123456789]{4,4}$",CRE4,BOOL_OP,AND,COMPOSITE_TEST,<Unused>,TEST_CLAUSE,"TEST @Value(CREDATE) CONTAINS_REGEX ^[0123456789]{6,6}$",CRE6,BOOL_OP,AND,COMPOSITE_TEST,<Unused>,TEST_CLAUSE,"TEST @Value(CREDATE) CONTAINS_REGEX ^[0123456789]{8,8}$",CRE8
    CRE4 -> TestFilter_5
    CRE6 -> SubstringExtractor_7
    CRE6 -> SubstringExtractor_4
    CRE8 -> SubstringExtractor_8
    CRE8 -> SubstringExtractor_6
    CRE8 -> SubstringExtractor_5
    <UNFILTERED> -> AttributeCreator_2
Note: AttributeCreator: Assignation d'un commentaire d'erreur.
Cloner_COPY_878 (output)

Bookmark: Year
SubstringExtractor_4
    END = 3
    RESULT_ATTR = CREDATE
    SRC_STRING = @Value(CREDATE)
    START = 0
    -> TestFilter_5
SubstringExtractor_5
    END = 3
    RESULT_ATTR = CREDATE
    SRC_STRING = @Value(CREDATE)
    START = 0
    -> TestFilter_5
TestFilter_5
    DEFAULT_VALUE = <UNFILTERED>
    TEST_LIST = BOOL_OP,AND,COMPOSITE_TEST,<Unused>,TEST_CLAUSE,"TEST @Value(CREDATE) NOT_>= 1960",1960,BOOL_OP,AND,COMPOSITE_TEST,<Unused>,TEST_CLAUSE,"TEST @Value(CREDATE) NOT_<= @Value(_timestamp_year)",timestamp
    1960 -> AttributeCreator_10
    timestamp -> AttributeCreator_14
AttributeCreator_10
    ATTR_TABLE = SET_TO COMMENT = ATTRIBUTE: Check year of CREDATE attribute for @Value(fme_feature_type)
    -> Cloner_COPY_878 (output)
AttributeCreator_14
    ATTR_TABLE = SET_TO COMMENT = ATTRIBUTE: Check CREDATE attribute for @Value(fme_feature_type)
    -> Cloner_COPY_878 (output)

Bookmark: Month
SubstringExtractor_6
    END = 5
    RESULT_ATTR = CREDATE
    SRC_STRING = @Value(CREDATE)
    START = 4
    -> TestFilter_6
SubstringExtractor_7
    END = 5
    RESULT_ATTR = CREDATE
    SRC_STRING = @Value(CREDATE)
    START = 4
    -> TestFilter_6
TestFilter_6
    DEFAULT_VALUE = <UNFILTERED>
    TEST_LIST:
      BOOL_OP,AND,COMPOSITE_TEST,<Unused>,TEST_CLAUSE,"TEST @Value(CREDATE) NOT_>= 01
      TEST @Value(CREDATE) NOT_<= 12",month_01_12,BOOL_OP,AND,COMPOSITE_TEST,<Unused>,TEST_CLAUSE,"TEST @Value(CREDATE) NOT_<= @Value(_timestamp_month)",timestamp
    month_01_12 -> AttributeCreator_11
    timestamp -> AttributeCreator_9
AttributeCreator_11
    ATTR_TABLE = SET_TO COMMENT = ATTRIBUTE: Check month of CREDATE attribute for @Value(fme_feature_type)
    -> Cloner_COPY_878 (output)
AttributeCreator_9
    ATTR_TABLE = SET_TO COMMENT = ATTRIBUTE: Check CREDATE attribute for @Value(fme_feature_type)
    -> Cloner_COPY_878 (output)

Bookmark: Day
SubstringExtractor_8
    END = 7
    RESULT_ATTR = CREDATE
    SRC_STRING = @Value(CREDATE)
    START = 6
    -> TestFilter_7
TestFilter_7
    DEFAULT_VALUE = <UNFILTERED>
    TEST_LIST:
      BOOL_OP,AND,COMPOSITE_TEST,<Unused>,TEST_CLAUSE,"TEST @Value(CREDATE) NOT_>= 01
      TEST @Value(CREDATE) NOT_<= 31",day_01_31,BOOL_OP,AND,COMPOSITE_TEST,<Unused>,TEST_CLAUSE,"TEST @Value(CREDATE) NOT_<= @Value(_timestamp_day)",timestamp
    day_01_31 -> AttributeCreator_12
    timestamp -> AttributeCreator_13
AttributeCreator_12
    ATTR_TABLE = SET_TO COMMENT = ATTRIBUTE: Check day of CREDATE attribute for @Value(fme_feature_type)
    -> Cloner_COPY_878 (output)
AttributeCreator_13
    ATTR_TABLE = SET_TO COMMENT = ATTRIBUTE: Check CREDATE attribute for @Value(fme_feature_type)
    -> Cloner_COPY_878 (output)
AttributeCreator_2
    ATTR_TABLE = SET_TO COMMENT = ATTRIBUTE: Check length of CREDATE attribute for @Value(fme_feature_type)
    -> Cloner_COPY_878 (output)
