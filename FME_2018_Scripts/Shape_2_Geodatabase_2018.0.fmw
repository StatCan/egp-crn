FME workspace Shape_2_Geodatabase_2018.0.fmw

Parameters:
- SourceDataset_SHAPE = ""E:\Work\NRN\NRN_PE_201703_deliverable\BLKPASSAGE.shp" "E:\Work\NRN\NRN_PE_201703_deliverable\FERRYSEG.shp" "E:\Work\NRN\NRN_PE_201703_deliverable\JUNCTION.shp" "E:\Work\NRN\NRN_PE_201703_deliverable\ROADSEG.shp" "E:\Work\NRN\NRN_PE_201703_deliverable\TOLLPOINT.shp""   # Source ESRI Shape File(s)
- SourceDataset_DBF =   # Source dBASE File(s)
- LOG_FILE =   # Log File
- CODE_PROV =
- DestDataset_FILEGDB = E:\Work\NRN\NRN\NRN.gdb   # File Geodatabase

Readers:
- SHAPE_1: SHAPE from $(SourceDataset_SHAPE) in LLCSRS
- DBF_1: DBF from $(SourceDataset_DBF)

Writers:
- FILEGDB_1: FILEGDB to $(DestDataset_FILEGDB)

Note: Version de compilation : 5206 / --REVISION-- $Id: shape2geodatabase.fmw 2672 2014-11-04 19:42:15Z dapoirie $
Note: Nom du workbench : shape2geodatabase / Auteur : Denis Bergeron / Date de création : 3 décembre 2007 / Description : Transfert des fichiers en format Shape et Dbf dans une géodatabase.

Bookmark: Géométries et attributs de base (SHAPE2MDB)
ROADSEG (reader SHAPE_1)
    attributes: NID char(32), ROADSEGID number(9,0), ADRANGENID char(32), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0),
      STRUCTID char(32), STRUCTTYPE number(4,0), STRUNAMEEN char(100), STRUNAMEFR char(100), CLOSING number(4,0), ROADJURIS char(100), SPEED number(4,0), TRAFFICDIR number(4,0)
    -> ParameterFetcher
    -> DuplicateCoordinateRemover
DuplicateCoordinateRemover
    CHECKZ = Yes
    MODE = Yes
    REPAIRED -> ROADSEG (writer FILEGDB_1)
    VALID -> ROADSEG (writer FILEGDB_1)
ROADSEG (writer FILEGDB_1)
    attributes: NID text(32), ROADSEGID double, ADRANGENID text(32), DATASETNAM double, SPECVERS text(100), ACQTECH double, ACCURACY double, PROVIDER double, CREDATE text(8), REVDATE text(8), METACOVER double, ROADCLASS double, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), EXITNBR text(10), NBRLANES double, PAVSTATUS double, PAVSURF double, UNPAVSURF double,
      STRUCTID text(32), STRUCTTYPE double, STRUNAMEEN text(100), STRUNAMEFR text(100), CLOSING double, ROADJURIS text(100), SPEED double, TRAFFICDIR double
FERRYSEG (reader SHAPE_1)
    attributes: NID char(32), FERRYSEGID number(9,0), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), CLOSING number(4,0)
    -> ParameterFetcher
    -> DuplicateCoordinateRemover_2
DuplicateCoordinateRemover_2
    CHECKZ = Yes
    MODE = Yes
    REPAIRED -> FERRYSEG (writer FILEGDB_1)
    VALID -> FERRYSEG (writer FILEGDB_1)
FERRYSEG (writer FILEGDB_1)
    attributes: NID text(32), FERRYSEGID double, DATASETNAM double, SPECVERS text(100), ACQTECH double, ACCURACY double, PROVIDER double, CREDATE text(8), REVDATE text(8), METACOVER double, ROADCLASS double, RTENAME1EN text(100), RTENAME2EN text(100), RTENAME3EN text(100), RTENAME4EN text(100), RTENAME1FR text(100), RTENAME2FR text(100), RTENAME3FR text(100), RTENAME4FR text(100), RTNUMBER1 text(10), RTNUMBER2 text(10), RTNUMBER3 text(10), RTNUMBER4 text(10), RTNUMBER5 text(10), CLOSING double
TOLLPOINT (reader SHAPE_1)
    attributes: NID char(32), DATASETNAM number(4,0), SPECVERS char(100), ACQTECH number(4,0), ACCURACY number(4,0), PROVIDER number(4,0), CREDATE char(8), REVDATE char(8), METACOVER number(4,0), TOLLPTTYPE number(4,0), ROADNID char(32)
    -> TOLLPOINT (writer FILEGDB_1)
    -> ParameterFetcher
TOLLPOINT (writer FILEGDB_1)
    attributes: NID text(32), DATASETNAM double, SPECVERS text(100), ACQTECH double, ACCURACY double, PROVIDER double, CREDATE text(8), REVDATE text(8), METACOVER double, TOLLPTTYPE double, ROADNID text(32)
BLKPASSAGE (reader SHAPE_1)
    attributes: NID char(32), DATASETNAM number(4,0), SPECVERS char(100), ACQTECH number(4,0), ACCURACY number(4,0), PROVIDER number(4,0), CREDATE char(8), REVDATE char(8), METACOVER number(4,0), BLKPASSTY number(4,0), ROADNID char(32)
    -> BLKPASSAGE (writer FILEGDB_1)
    -> ParameterFetcher
BLKPASSAGE (writer FILEGDB_1)
    attributes: NID text(32), DATASETNAM double, SPECVERS text(100), ACQTECH double, ACCURACY double, PROVIDER double, CREDATE text(8), REVDATE text(8), METACOVER double, BLKPASSTY double, ROADNID text(32)
JUNCTION (reader SHAPE_1)
    attributes: NID char(32), DATASETNAM number(4,0), SPECVERS char(100), ACQTECH number(4,0), ACCURACY number(4,0), PROVIDER number(4,0), CREDATE char(8), REVDATE char(8), METACOVER number(4,0), JUNCTYPE number(4,0), EXITNBR char(10)
    -> JUNCTION (writer FILEGDB_1)
    -> ParameterFetcher
JUNCTION (writer FILEGDB_1)
    attributes: NID text(32), DATASETNAM double, SPECVERS text(100), ACQTECH double, ACCURACY double, PROVIDER double, CREDATE text(8), REVDATE text(8), METACOVER double, JUNCTYPE double, EXITNBR text(10)
CROSSING (reader SHAPE_1)
    attributes: NID char(32), DATASETNAM number(4,0), SPECVERS char(100), ACQTECH number(4,0), ACCURACY number(4,0), PROVIDER number(4,0), CREDATE char(8), REVDATE char(8), METACOVER number(4,0), TYPE number(4,0), ROADNID char(32)
    -> CROSSING (writer FILEGDB_1)
    -> ParameterFetcher
CROSSING (writer FILEGDB_1)
    attributes: NID text(32), DATASETNAM double, SPECVERS text(100), ACQTECH double, ACCURACY double, PROVIDER double, CREDATE text(8), REVDATE text(8), METACOVER double, TYPE double, ROADNID text(32)

Bookmark: Adresses (DBF2MDB)
ADDRANGE (reader DBF_1)
    attributes: NID char(32), DATASETNAM number(4,0), SPECVERS char(100), ACQTECH number(4,0), ACCURACY number(4,0), PROVIDER number(4,0), CREDATE char(8), REVDATE char(8), METACOVER number(4,0), L_DIGDIRFG number(4,0), L_HNUMSTR number(4,0), L_RFSYSIND number(4,0), L_HNUMTYPF number(4,0), L_HNUMF number(9,0), L_HNUMSUFF char(20), L_HNUMTYPL number(4,0), L_HNUML number(9,0), L_HNUMSUFL char(20), L_OFFNANID char(32), L_ALTNANID char(32), R_DIGDIRFG number(4,0), R_HNUMSTR number(4,0), R_RFSYSIND number(4,0), R_HNUMTYPF number(4,0), R_HNUMF number(9,0), R_HNUMSUFF char(20), R_HNUMTYPL number(4,0), R_HNUML number(9,0), R_HNUMSUFL char(20), R_OFFNANID char(32),
      R_ALTNANID char(32)
    -> ADDRANGE (writer FILEGDB_1)
    -> ParameterFetcher
ADDRANGE (writer FILEGDB_1)
    attributes: NID text(32), DATASETNAM double, SPECVERS text(100), ACQTECH double, ACCURACY double, PROVIDER double, CREDATE text(8), REVDATE text(8), METACOVER double, L_DIGDIRFG double, L_HNUMSTR double, L_RFSYSIND double, L_HNUMTYPF double, L_HNUMF double, L_HNUMSUFF text(20), L_HNUMTYPL double, L_HNUML double, L_HNUMSUFL text(20), L_OFFNANID text(32), L_ALTNANID text(32), R_DIGDIRFG double, R_HNUMSTR double, R_RFSYSIND double, R_HNUMTYPF double, R_HNUMF double, R_HNUMSUFF text(20), R_HNUMTYPL double, R_HNUML double, R_HNUMSUFL text(20), R_OFFNANID text(32),
      R_ALTNANID text(32)
ALTNAMLINK (reader DBF_1)
    attributes: NID char(32), STRNAMENID char(32), DATASETNAM number(4,0), SPECVERS char(100), CREDATE char(8), REVDATE char(8)
    -> ALTNAMLINK (writer FILEGDB_1)
    -> ParameterFetcher
ALTNAMLINK (writer FILEGDB_1)
    attributes: NID text(32), STRNAMENID text(32), DATASETNAM double, SPECVERS text(100), CREDATE text(8), REVDATE text(8)
STRPLANAME (reader DBF_1)
    attributes: NID char(32), DATASETNAM number(4,0), SPECVERS char(100), ACQTECH number(4,0), ACCURACY number(4,0), PROVIDER number(4,0), CREDATE char(8), REVDATE char(8), METACOVER number(4,0), DIRPREFIX number(4,0), STRTYPRE char(30), STARTICLE char(20), NAMEBODY char(50), STRTYSUF char(30), DIRSUFFIX number(4,0), MUNIQUAD number(4,0), PLACENAME char(100), PROVINCE number(4,0), PLACETYPE char(100)
    -> STRPLANAME (writer FILEGDB_1)
    -> ParameterFetcher
STRPLANAME (writer FILEGDB_1)
    attributes: NID text(32), DATASETNAM double, SPECVERS text(100), ACQTECH double, ACCURACY double, PROVIDER double, CREDATE text(8), REVDATE text(8), METACOVER double, DIRPREFIX double, STRTYPRE text(30), STARTICLE text(20), NAMEBODY text(50), STRTYSUF text(30), DIRSUFFIX double, MUNIQUAD double, PLACENAME text(100), PROVINCE double, PLACETYPE text(100)

Bookmark: Valider DatasetNam vs code province
ParameterFetcher
    ATTR_LIST = _codeProvince {$(CODE_PROV)}
    -> AttributeValueMapper
AttributeValueMapper
    DIRECTION = Forward (Source To Destination)
    LUT = NL,1,NS,2,PE,3,NB,4,QC,5,ON,6,MB,7,SK,8,AB,9,BC,10,YT,11,NT,12,NU,13
    SRC = _codeProvince
    VAL_ATTR = _CodeProvinceNumber
    -> Tester
Tester
    BOOL_OP = OR
    TEST_CLAUSE = TEST @Value(DATASETNAM) = @Value(_CodeProvinceNumber)
    FAILED -> Terminator
Terminator
    MESSAGE = Translation Terminated
