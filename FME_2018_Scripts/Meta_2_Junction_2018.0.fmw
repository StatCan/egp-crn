FME workspace Meta_2_Junction_2018.0.fmw

Parameters:
- SourceDataset_SHAPE = E:\Work\NRN\NRN_PE_201703_deliverable\BLKPASSAGE.shp   # Source ESRI Shape File(s)
- DestDataset_SHAPE =   # Destination Shape File Directory
- LOG_FILE =   # Log File

Readers:
- ESRISHAPE_1: ESRISHAPE from $(SourceDataset_SHAPE)

Writers:
- ESRISHAPE_2: ESRISHAPE to $(DestDataset_SHAPE)

Note: Version de compilation : 5206 / --REVISION-- $Id: meta2junction.fmw 1242 2011-04-11 18:45:05Z ddrolet $
Note: Nom du workbench : meta2junction / Auteur : Denis Bergeron / Date de création : 12-juil-2007 / Description : Assignation de métadonnées aux jonctions à partir de celles des routes et des traverses.
ROADSEG (reader ESRISHAPE_1)
    attributes: NID char(32), ROADSEGID number(9,0), ADRANGENID char(32), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0),
      STRUCTID char(32), STRUCTTYPE number(4,0), STRUNAMEEN char(100), STRUNAMEFR char(100), CODEPROV char(25)
    -> ATTRIBUTECREATOR
FERRYSEG (reader ESRISHAPE_1)
    attributes: NID char(32), FERRYSEGID number(9,0), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10)
    -> ATTRIBUTECREATOR
Note: Assignation de / l'origine.
ATTRIBUTECREATOR: AttributeCreator
    ATTR_TABLE = SET_TO ORIGINE = LIGNE
    -> ATTRIBUTEKEEPER
Note: Conservation des attributs / de métadonnées.
ATTRIBUTEKEEPER: AttributeKeeper
    KEEP_ATTRS = ACCURACY,CREDATE,NID,ORIGINE,REVDATE
    -> COORDINATEFETCHER
    -> COORDINATEFETCHER_2
Note: Extraction de la / première coordonnée.
COORDINATEFETCHER: CoordinateExtractor
    IND = 0
    MODE = Specify Coordinate
    X_ATTR = x
    Y_ATTR = y
    Z_ATTR = z
    Z_DEFAULT = -9999
    -> VertexCreator
Note: Extraction de la / deuxième coordonnée.
COORDINATEFETCHER_2: CoordinateExtractor
    IND = -1
    MODE = Specify Coordinate
    X_ATTR = x
    Y_ATTR = y
    Z_ATTR = z
    Z_DEFAULT = -9999
    -> VertexCreator
Note: Création de points.
VertexCreator
    MODE_NAME = Replace with Point
    XVAL = @Value(x)
    YVAL = @Value(y)
    -> COORDINATEROUNDER_2
Note: Arrondisssment / des coordonnées.
COORDINATEROUNDER_2: CoordinateRounder
    XPREC = 7
    YPREC = 7
    ZPREC = 0
    ROUNDED -> STRINGLENGTHCALCULATOR_3
Note: Calcul de la longueur / de l'attribut CREDATE.
STRINGLENGTHCALCULATOR_3: StringLengthCalculator
    LENGTH_ATTR = long_credate
    SRC_ATTR = CREDATE
    -> AttributeFilter
AttributeFilter
    ATTR_NAME = long_credate
    ATTR_VALUES = 4,6,8
    4 -> CONCATENATOR_5
    6 -> CONCATENATOR_2
    8 -> Cloner
Note: Concaténation de / valeurs par défaut / à l'attribut CREDATE.
CONCATENATOR_5: StringConcatenator
    ACTION = Create New Attribute
    PARM_LINE = @Value(CREDATE)0000
    VAL_ATTR = CREDATE
    -> Cloner
Note: Concaténation de / valeurs par défaut / à l'attribut CREDATE.
CONCATENATOR_2: StringConcatenator
    ACTION = Create New Attribute
    PARM_LINE = @Value(CREDATE)00
    VAL_ATTR = CREDATE
    -> Cloner
Cloner
    COPIES = 1
    COPYATT = _copynum
    COPY -> STRINGLENGTHCALCULATOR_2
Note: Calcul de la longueur / de l'attribut REVDATE.
STRINGLENGTHCALCULATOR_2: StringLengthCalculator
    LENGTH_ATTR = long_revdate
    SRC_ATTR = REVDATE
    -> AttributeFilter_2
AttributeFilter_2
    ATTR_NAME = long_revdate
    ATTR_VALUES = 4,6,8
    4 -> CONCATENATOR_3
    6 -> CONCATENATOR_4
    8 -> Cloner_2
Note: Concaténation de / valeurs par défaut / à l'attribut REVDATE.
CONCATENATOR_3: StringConcatenator
    ACTION = Create New Attribute
    PARM_LINE = @Value(REVDATE)0000
    VAL_ATTR = REVDATE
    -> Cloner_2
Note: Concaténation de / valeurs par défaut / à l'attribut REVDATE.
CONCATENATOR_4: StringConcatenator
    ACTION = Create New Attribute
    PARM_LINE = @Value(REVDATE)00
    VAL_ATTR = REVDATE
    -> Cloner_2
Cloner_2
    COPIES = 1
    COPYATT = _copynum
    COPY -> MATCHER
JUNCTION (reader ESRISHAPE_1)
    attributes: NID char(32), DATASETNAM number(4,0), SPECVERS char(100), ACQTECH number(4,0), ACCURACY number(4,0), PROVIDER number(4,0), CREDATE char(8), REVDATE char(8), METACOVER number(4,0), JUNCTYPE number(4,0), EXITNBR char(10)
    -> ATTRIBUTECREATOR_2
Note: Assignation de / l'origine.
ATTRIBUTECREATOR_2: AttributeCreator
    ATTR_TABLE = SET_TO ORIGINE = POINT
    -> ATTRIBUTEREMOVER
Note: Retrait des attributs / de métadonnées.
ATTRIBUTEREMOVER: AttributeRemover
    REMOVE_ATTRS = ACCURACY,ACQTECH,CREDATE,PROVIDER,REVDATE,METACOVER
    -> ATTRIBUTECOPIER
Note: Copie de l'attribut NID / dans l'attribut NIDJCT.
ATTRIBUTECOPIER: AttributeCopier
    ATTR_TABLE = COPY NID > NIDJCT
    -> COORDINATEROUNDER
Note: Arrondisssment / des coordonnées.
COORDINATEROUNDER: CoordinateRounder
    XPREC = 7
    YPREC = 7
    ZPREC = 0
    ROUNDED -> MATCHER
Note: Mise en correspondance / des jonctions et des routes.
MATCHER: Matcher
    BLANK_AND_MISSING_DIFFER = No
    CNT_ATTR = _match_id
    DIFFATTRS = NID ORIGINE
    EXTRA_VERTEX_TOLERANCE = 1E-7
    INTERIOR_VERTEX_TOLERANCE = 1E-7
    LENIENT_MATCH = No
    MATCH = 2D
    MATCH_STRATEGY = Match Selected Attributes
    SM_LIST_NAME = meta
    SINGLE_MATCHED -> LISTRANGEEXTRACTOR
Note: Extraction des dates / de création.
LISTRANGEEXTRACTOR: ListRangeExtractor
    MAX = _max_CREDATE
    MIN = _min_CREDATE
    SRC_LIST = meta{}.CREDATE
    -> LISTRANGEEXTRACTOR_4
Note: Extraction des dates / de révision.
LISTRANGEEXTRACTOR_4: ListRangeExtractor
    MAX = _max_REVDATE
    MIN = _min_REVDATE
    SRC_LIST = meta{}.REVDATE
    -> LISTRANGEEXTRACTOR_2
Note: Extraction des précisions.
LISTRANGEEXTRACTOR_2: ListRangeExtractor
    MAX = _max_ACCURACY
    MIN = _min_ACCURACY
    SRC_LIST = meta{}.ACCURACY
    -> ATTRIBUTERENAMER_6
Note: Assignation des métadonnées.
ATTRIBUTERENAMER_6: AttributeRenamer
    ATTR_TABLE:
      RENAME_SET_DEFAULT _min_CREDATE > CREDATE
      RENAME_SET_DEFAULT _max_ACCURACY > ACCURACY
      RENAME_SET_DEFAULT _max_REVDATE > REVDATE
    -> AttributeTrimmer_2
AttributeTrimmer_2
    SRC_ATTRS = CREDATE
    TRIM_CHARS = 0
    TRIM_TO_NONE = No
    TRIM_TYPE = Right
    -> STRINGLENGTHCALCULATOR_9
Note: Calcul de la longueur / de l'attribut CREDATE.
STRINGLENGTHCALCULATOR_9: StringLengthCalculator
    LENGTH_ATTR = long_credate
    SRC_ATTR = CREDATE
    -> AttributeFilter_8
AttributeFilter_8
    ATTR_NAME = long_credate
    ATTR_VALUES = 1,2,3,5,7
    1 -> CONCATENATOR_9
    2 -> CONCATENATOR_10
    3 -> CONCATENATOR_11
    5 -> CONCATENATOR_11
    7 -> CONCATENATOR_11
Note: Concaténation de / valeurs par défaut / à l'attribut REVDATE.
CONCATENATOR_9: StringConcatenator
    ACTION = Create New Attribute
    PARM_LINE = @Value(CREDATE)000
    VAL_ATTR = CREDATE
    -> Cloner_3
Note: Concaténation de / valeurs par défaut / à l'attribut CREDATE.
CONCATENATOR_10: StringConcatenator
    ACTION = Create New Attribute
    PARM_LINE = @Value(CREDATE)00
    VAL_ATTR = CREDATE
    -> Cloner_3
Note: Concaténation de / valeurs par défaut / à l'attribut CREDATE.
CONCATENATOR_11: StringConcatenator
    ACTION = Create New Attribute
    PARM_LINE = @Value(CREDATE)0
    VAL_ATTR = CREDATE
    -> Cloner_3
Cloner_3
    COPIES = 1
    COPYATT = _copynum
    COPY -> AttributeTrimmer_3
AttributeTrimmer_3
    SRC_ATTRS = REVDATE
    TRIM_CHARS = 0
    TRIM_TO_NONE = No
    TRIM_TYPE = Right
    -> STRINGLENGTHCALCULATOR_8
Note: Calcul de la longueur / de l'attribut REVDATE.
STRINGLENGTHCALCULATOR_8: StringLengthCalculator
    LENGTH_ATTR = long_revdate
    SRC_ATTR = REVDATE
    -> AttributeFilter_7
AttributeFilter_7
    ATTR_NAME = long_revdate
    ATTR_VALUES = 1,2,3,5,7
    1 -> CONCATENATOR_6
    2 -> CONCATENATOR_7
    3 -> CONCATENATOR_8
    5 -> CONCATENATOR_8
    7 -> CONCATENATOR_8
Note: Concaténation de / valeurs par défaut / à l'attribut REVDATE.
CONCATENATOR_6: StringConcatenator
    ACTION = Create New Attribute
    PARM_LINE = @Value(REVDATE)000
    VAL_ATTR = REVDATE
    -> Cloner_4
Note: Concaténation de / valeurs par défaut / à l'attribut REVDATE.
CONCATENATOR_7: StringConcatenator
    ACTION = Create New Attribute
    PARM_LINE = @Value(REVDATE)00
    VAL_ATTR = REVDATE
    -> Cloner_4
Note: Concaténation de / valeurs par défaut / à l'attribut REVDATE.
CONCATENATOR_8: StringConcatenator
    ACTION = Create New Attribute
    PARM_LINE = @Value(REVDATE)0
    VAL_ATTR = REVDATE
    -> Cloner_4
Cloner_4
    COPIES = 1
    COPYATT = _copynum
    COPY -> ATTRIBUTECREATOR_6
Note: Assignation des attributs / ACQTECH et PROVIDER.
ATTRIBUTECREATOR_6: AttributeCreator
    ATTR_TABLE:
      SET_TO ACQTECH = 12
      SET_TO PROVIDER = 3
      SET_TO METACOVER = 1
    -> ATTRIBUTECOPIER_2
Note: Copie de l'attribut NIDJCT / dans l'attribut NID.
ATTRIBUTECOPIER_2: AttributeCopier
    ATTR_TABLE = COPY NIDJCT > NID
    -> STRINGLENGTHCALCULATOR
Note: Détermination de la / longueur de l'attribut NIDJCT.
STRINGLENGTHCALCULATOR: StringLengthCalculator
    LENGTH_ATTR = _length
    SRC_ATTR = NIDJCT
    -> TESTER
Note: Sélection des jonctions.
TESTER: Tester
    BOOL_OP = OR
    TEST_CLAUSE = TEST @Value(_length) = 32
    PASSED -> JUNCTION_WITH_META (writer ESRISHAPE_2)
JUNCTION_WITH_META (writer ESRISHAPE_2)
    attributes: NID char(32), DATASETNAM number(4,0), SPECVERS char(100), ACQTECH number(4,0), ACCURACY number(4,0), PROVIDER number(4,0), CREDATE char(8), REVDATE char(8), METACOVER number(4,0), JUNCTYPE number(4,0), EXITNBR char(10)
