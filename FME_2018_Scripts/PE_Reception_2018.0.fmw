FME workspace PE_Reception_2018.0.fmw

Parameters:
- DestDataset_SHAPE = C:\rrngeo\PE\Incoming   # Destination Shape File Directory
- SourceDataset_ESRISHAPE_3 = W:\Travail\rrngeo\pro\ShapePE\Incoming\PEI_NRN17.shp   # Source Esri Shapefile(s)

Readers:
- ESRISHAPE_1: ESRISHAPE from $(SourceDataset_ESRISHAPE_3)

Writers:
- SHAPE_1: SHAPE to $(DestDataset_SHAPE) in EPSG:4617

PEI_NRN17 (reader ESRISHAPE_1)
    attributes: NID char(32), ROADSEGID number(11,0), ADRANGENID char(32), DATASETNAM long, SPECVERS char(100), ACQTECH long, ACCURACY long, PROVIDER long, CREDATE char(8), REVDATE char(8), METACOVER long, ROADCLASS long, RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES long, PAVSTATUS long, PAVSURF long, UNPAVSURF long,
      STRUCTID char(32), STRUCTTYPE long, STRUNAMEEN char(100), STRUNAMEFR char(100), TRAFFICDIR long, ROADJURIS char(100), CLOSING long, SPEED long, OLD_KEY char(10), STREET_NM char(50), LENGTH double, MANAGE_SYS char(10), PROVID char(36), SHAPE_LENG double, SURFACE char(10), M_ZONE char(10), COMMUNITY char(20), DIST_NO number(11,0), ELECT_DIST char(50), COUNTY1 char(3), OWNER_SURF char(20), TNID char(32), NAMEBODY char(50), DIRSUFFIX char(4), DIRPREFIX char(4), STRTYPRE char(30), STRTYSUF char(30), PLACE_L char(100), PLACE_R char(100), NAME char(50),
      L_HNUMF number(11,0), R_HNUMF number(11,0), L_HNUML number(11,0), R_HNUML number(11,0), A_REGS char(12), DONE long, OID_ number(11,0), L_DIGDIRFG long, L_HNUMSTR long, L_RFSYSIND long, L_HNUMTYPF long, L_HNUMSUFF char(20), L_HNUMTYPL long, L_HNUMSUFL char(20), L_ALTNANID char(32), R_DIGDIRFG long, R_HNUMSTR long, R_RFSYSIND long, R_HNUMTYPF long, R_HNUMSUFF char(20), R_HNUMTYPL long, R_HNUMSUFL char(20), R_ALTNANID char(32), EXP_FUND char(12), YEAR_BUILT char(4)
    -> Reprojector
Reprojector
    DEST = EPSG:4617
    INTERPOLATION_TYPE_NAME = Nearest Neighbor
    RASTER_CELL_SIZE = Preserve Cells
    SOURCE = PEI_New_CSRS
    STROKE_ARCS = Yes
    REPROJECTED -> CoordinateRounder
CoordinateRounder
    XPREC = 7
    YPREC = 7
    ZPREC = 0
    ROUNDED -> AttributeRemover
AttributeRemover
    REMOVE_ATTRS = NID
    -> Counter_3
Counter_3
    CNT_ATTR = _ID_TEMP
    DOMAIN = counter
    SCOPE = Global
    START = 0
    -> LineJoiner_4
    -> FeatureMerger_6 [REQUESTOR]
LineJoiner_4
    BREAK = no
    CONSIDER_NODE_ELEVATION = no
    GROUP_BREAK = no
    LIST_NAME = SegList
    PRESERVE = no
    TOPOLOGY = End noded
    LINE -> UUIDGenerator
UUIDGenerator
    UUID_ATTR = NID
    -> ListIndexer_2
ListIndexer_2
    INDEX = 0
    LIST_ATTR = SegList{}
    -> ListExploder
ListExploder
    INDEX_ATTR = _element_index
    LIST_ATTR = SegList{}
    MODE = List Elements and Original Attributes
    -> AttributeKeeper_3
AttributeKeeper_3
    KEEP_ATTRS = NID,_ID_TEMP
    -> FeatureMerger_6 [SUPPLIER]
FeatureMerger_6
    BUILD_INCOMPLETE = No
    MERGE_TYPE = Attributes Only
    PROCESS_DUPS = No
    REFEEATTR = _ID_TEMP
    REFERATTR = _ID_TEMP
    COMPLETE -> ROADSEG (writer SHAPE_1)
    INCOMPLETE -> Terminator
ROADSEG (writer SHAPE_1)
    attributes: NID char(32), ROADSEGID number(9,0), ADRANGENID char(32), DATASETNAM number(4,0), SPECVERS char(100), ACQTECH number(4,0), ACCURACY number(4,0), PROVIDER number(4,0), CREDATE char(8), REVDATE char(8), METACOVER number(4,0), ROADCLASS number(4,0), RTENAME1EN char(100), RTENAME2EN char(100), RTENAME3EN char(100), RTENAME4EN char(100), RTENAME1FR char(100), RTENAME2FR char(100), RTENAME3FR char(100), RTENAME4FR char(100), RTNUMBER1 char(10), RTNUMBER2 char(10), RTNUMBER3 char(10), RTNUMBER4 char(10), RTNUMBER5 char(10), EXITNBR char(10), NBRLANES number(4,0), PAVSTATUS number(4,0), PAVSURF number(4,0), UNPAVSURF number(4,0),
      STRUCTID char(32), STRUCTTYPE number(8,0), STRUNAMEEN char(100), STRUNAMEFR char(100), TRAFFICDIR number(4,0), ROADJURIS char(100), CLOSING number(4,0), SPEED number(9,0), OLD_KEY char(10), STREET_NM char(50), LENGTH number(31,15), MANAGE_SYS char(10), PROVID char(36), SHAPE_LENG number(31,15), SURFACE char(10), M_ZONE char(10), COMMUNITY char(20), DIST_NO number(9,0), ELECT_DIST char(50), COUNTY1 char(3), OWNER_SURF char(20), TNID char(32), NAMEBODY char(50), DIRSUFFIX number(4,0), DIRPREFIX number(4,0), STRTYPRE char(30), STRTYSUF char(30), PLACE_L char(100), PLACE_R char(100), NAME char(50),
      L_HNUMF number(9,0), R_HNUMF number(9,0), L_HNUML number(9,0), R_HNUML number(9,0), A_REGS char(12), DONE number(9,0), OID_ number(9,0), L_DIGDIRFG number(4,0), L_HNUMSTR number(4,0), L_RFSYSIND number(4,0), L_HNUMTYPF number(4,0), L_HNUMSUFF char(20), L_HNUMTYPL number(4,0), L_HNUMSUFL char(20), L_ALTNANID char(32), R_DIGDIRFG number(4,0), R_HNUMSTR number(4,0), R_RFSYSIND number(4,0), R_HNUMTYPF number(4,0), R_HNUMSUFF char(20), R_HNUMTYPL number(4,0), R_HNUMSUFL char(20), R_ALTNANID char(32), EXP_FUND char(12), YEAR_BUILT char(4)
Terminator
    MESSAGE = Donnees perdues lors du traitement
